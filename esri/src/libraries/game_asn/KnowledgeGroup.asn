--
-- file name : AutomatetAttr.asn
--
-- Messages de gestion des attributs d'une unité
--

KnowledgeGroup DEFINITIONS AUTOMATIC TAGS ::= BEGIN

-- BEGIN includes
IMPORTS BaseExports FROM Base;
KnowledgeGroupIncludes ::= SEQUENCE { BaseExports }
KnowledgeGroupExports  ::= NULL
-- END includes

MsgKnowledgeGroupCreation ::= SEQUENCE
{
    oid         KnowledgeGroup,
    oid-camp    Camp
}

END -- KnowledgeGroup
