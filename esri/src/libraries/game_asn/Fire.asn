--
-- file name : Fire.asn
--
-- Messages de gestion des tirs
--

Fire DEFINITIONS AUTOMATIC TAGS ::= BEGIN

-- BEGIN includes
IMPORTS BaseExports FROM Base;
FireIncludes ::= SEQUENCE { BaseExports }
FireExports  ::= NULL
-- END includes

FireDamagePionHuman ::= SEQUENCE
{
    rang                        EnumHumanRank,
    nb-non-blesses              INTEGER, -- NB : toutes les valeurs peuvent être négatives
    nb-morts                    INTEGER,
    nb-blesses-urgence-1        INTEGER,
    nb-blesses-urgence-2        INTEGER,
    nb-blesses-urgence-3        INTEGER,
    nb-blesses-urgence-extreme  INTEGER
}

FireDamagePionEquipment ::= SEQUENCE
{
    type-equipement  TypeEquipement,
    nb-disponibles   INTEGER,
    nb-indisponibles INTEGER,
    nb-reparables    INTEGER
}

FireDamagesPion ::= SEQUENCE
{
    cible       Agent,
    humains     SEQUENCE OF FireDamagePionHuman,
    equipements SEQUENCE OF FireDamagePionEquipment
}

FireDamagesPopulation ::= SEQUENCE
{
    cible       Population,
    nb-morts    INTEGER
}

FireDamagesPions       ::= SEQUENCE OF FireDamagesPion
FireDamagesPopulations ::= SEQUENCE OF FireDamagesPopulation

-- Tir pion
MsgStartPionFire ::= SEQUENCE
{
    oid-tir     TirPion,
    tireur      Agent,
    cible       CHOICE
    {
        pion       Agent,
        population Population,
        position   CoordUTM
    },
    type        ENUMERATED
    {
        direct,
        indirect
    },
    munition    TypeDotation OPTIONAL
}

MsgStopPionFire ::= SEQUENCE
{
    oid-tir            TirPion,
    degats-pions       FireDamagesPions,
    degats-populations FireDamagesPopulations
}

-- Tir population
MsgStartPopulationFire ::= SEQUENCE
{
    oid-tir     TirPopulation,
    oid-src     Population
}

MsgStopPopulationFire ::= SEQUENCE
{
    oid-tir      TirPopulation,
    degats-pions FireDamagesPions
}

-- Explosion mine
MsgExplosion ::= SEQUENCE
{
    oid-objet          OID,
    degats-pions       FireDamagesPions,
    degats-populations FireDamagesPopulations
}

-- Effets de tirs
EnumFireEffectType ::= ENUMERATED
{
    fumigene    (0),
    eclairant   (1)
}

MsgStartFireEffect ::= SEQUENCE
{
    oid-effet       OID,
    localisation    Localisation,
    type            EnumFireEffectType
}

MsgStopFireEffect ::= OID


END -- Fire
