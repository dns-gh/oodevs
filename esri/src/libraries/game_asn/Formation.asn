--
-- file name : AutomatetAttr.asn
--
-- Messages de gestion des attributs d'une unité
--

Formation DEFINITIONS AUTOMATIC TAGS ::= BEGIN

-- BEGIN includes
IMPORTS BaseExports FROM Base;
FormationIncludes ::= SEQUENCE { BaseExports }
FormationExports  ::= NULL
-- END includes

MsgFormationCreation ::= SEQUENCE
{
    oid                     Formation,
    oid-camp                Camp,
    oid-formation-parente   Formation OPTIONAL,
    niveau                  EnumNatureLevel,
    nom                     VisibleString          
}

END -- Formation
