--
-- file name : Games.asn
--
-- Games messages
--

Games DEFINITIONS AUTOMATIC TAGS ::= BEGIN

-- BEGIN includes
GamesIncludes ::= SEQUENCE {}
GamesExports  ::= NULL
-- END includes

Game ::= SEQUENCE
{
    name            VisibleString,
    host            VisibleString,
    exercise-name   VisibleString,
    start-date      VisibleString,
    status          ENUMERATED
    {
        running,
        paused
    }
}

GameList ::= SEQUENCE OF Game

END
