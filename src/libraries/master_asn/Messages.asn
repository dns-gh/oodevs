--
-- file name : Messages.asn
--
-- Messages list
--

Messages DEFINITIONS AUTOMATIC TAGS ::= BEGIN

-- BEGIN includes
IMPORTS ProfilesExports  FROM Profiles
        DataExports      FROM Data
        ExercisesExports FROM Exercises
        GamesExports     FROM Games;
MessagesIncludes ::= SEQUENCE { ProfilesExports, ExercisesExports, GamesExports, DataExports }
MessagesExports  ::= NULL
-- END includes

MsgsInMaster ::= SEQUENCE
{
    context INTEGER DEFAULT 0,
    msg     CHOICE
    {
        -- profiles
        msg-authentication-request          MsgAuthenticationRequest,
        -- exercises
        msg-exercise-creation-request       MsgExerciseCreationRequest,
        msg-exercise-update-request         MsgExerciseUpdateRequest,
        msg-exercise-destruction-request    MsgExerciseDestructionRequest
        
        -- games
    }
}

MsgsOutMaster ::= SEQUENCE
{
    context INTEGER DEFAULT 0,
    msg     CHOICE
    {
        -- profiles
        msg-authentication-response     MsgAuthenticationResponse,
        
        -- data
        msg-dataset-creation            MsgDatasetCreation,
        msg-terrain-creation            MsgTerrainCreation,
        msg-physical-model-creation     MsgPhysicalModelCreation,
                
        -- exercises
        msg-exercise-creation           MsgExerciseCreation,
        msg-exercise-update             MsgExerciseUpdate,
        msg-exercise-destruction        MsgExerciseDestruction,
        msg-exercise-creation-ack       MsgExerciseCreationRequestAck,
        msg-exercise-update-ack         MsgExerciseUpdateRequestAck,
        msg-exercise-destruction-ack    MsgExerciseDestructionRequestAck
        
        -- games
    }
}

END
