--
-- file name : ScipioMessages.asn
--
-- Liste des messages
--

ScipioMessages DEFINITIONS AUTOMATIC TAGS ::= BEGIN

-- BEGIN includes
IMPORTS ScipioBaseExports                   FROM ScipioBase
        ScipioLimaLimiteExports             FROM ScipioLimaLimite
        ScipioOrderExports                  FROM ScipioOrder
        ScipioControlExports                FROM ScipioControl
        ScipioKnowledgeGroupExports         FROM ScipioKnowledgeGroup
        ScipioFormationExports              FROM ScipioFormation
        ScipioFireExports                   FROM ScipioFire
        ScipioUnitExports                   FROM ScipioUnit
        ScipioUnitKnowledgeExports          FROM ScipioUnitKnowledge
        ScipioObjectExports                 FROM ScipioObject
        ScipioObjectKnowledgeExports        FROM ScipioObjectKnowledge
        ScipioPopulationExports             FROM ScipioPopulation
        ScipioPopulationKnowledgeExports    FROM ScipioPopulationKnowledge
        ScipioLogMaintenanceExports         FROM ScipioLogMaintenance
        ScipioLogRavitaillementExports      FROM ScipioLogRavitaillement
        ScipioLogSanteExports               FROM ScipioLogSante
        ScipioAutomateExports               FROM ScipioAutomate
        ScipioArmyExports                   FROM ScipioArmy
        ScipioAuthExports                   FROM ScipioAuth;
ScipioMessagesIncludes ::= SEQUENCE
{ ScipioBaseExports, ScipioLimaLimiteExports, ScipioOrderExports, ScipioControlExports, ScipioKnowledgeGroupExports, 
  ScipioFormationExports, ScipioFireExports, ScipioUnitExports, ScipioUnitKnowledgeExports, ScipioObjectExports, 
  ScipioObjectKnowledgeExports, ScipioPopulationExports, ScipioPopulationKnowledgeExports, ScipioLogMaintenanceExports,
  ScipioLogRavitaillementExports, ScipioLogSanteExports, ScipioAutomateExports, ScipioArmyExports, ScipioAuthExports }
ScipioMessagesExports  ::= NULL
-- END includes

--
-- 
--  
MsgsOutSim ::= SEQUENCE
{
    context INTEGER DEFAULT 0,
    msg     CHOICE
    {
        -- ACKS
        msg-limit-creation-request-ack                          MsgLimitCreationRequestAck,
        msg-limit-destruction-request-ack                       MsgLimitDestructionRequestAck,
        msg-limit-update-request-ack                            MsgLimitUpdateRequestAck,
        msg-lima-creation-request-ack                           MsgLimaCreationRequestAck,
        msg-lima-destruction-request-ack                        MsgLimaDestructionRequestAck,
        msg-lima-update-request-ack                             MsgLimaUpdateRequestAck,

        msg-pion-order-ack                                      MsgPionOrderAck,
        msg-automate-order-ack                                  MsgAutomateOrderAck,
        msg-population-order-ack                                MsgPopulationOrderAck,
        msg-frag-order-ack                                      MsgFragOrderAck,                                                                
        msg-set-automate-mode-ack                               MsgSetAutomateModeAck,

        msg-unit-magic-action-ack                               MsgUnitMagicActionAck,
        msg-object-magic-action-ack                             MsgObjectMagicActionAck,
        msg-population-magic-action-ack                         MsgPopulationMagicActionAck,

        msg-change-diplomatie-ack                               MsgChangeDiplomatieAck,
        msg-change-groupe-connaissance-ack                      MsgChangeGroupeConnaissanceAck,
        msg-change-liens-logistiques-ack                        MsgChangeLiensLogistiquesAck,
        msg-change-automate-ack                                 MsgChangeAutomateAck,   

        msg-log-ravitaillement-pousser-flux-ack                 MsgLogRavitaillementPousserFluxAck,
        msg-log-ravitaillement-change-quotas-ack                MsgLogRavitaillementChangeQuotasAck,   

        -- MESSAGES
        msg-ctrl-info                                           MsgCtrlInfo,
        msg-ctrl-begin-tick                                     MsgCtrlBeginTick,
        msg-ctrl-end-tick                                       MsgCtrlEndTick,
        msg-ctrl-stop-ack                                       MsgCtrlStopAck,
        msg-ctrl-pause-ack                                      MsgCtrlPauseAck,
        msg-ctrl-resume-ack                                     MsgCtrlResumeAck,
        msg-ctrl-change-time-factor-ack                         MsgCtrlChangeTimeFactorAck,
        msg-ctrl-meteo-globale-ack                              MsgCtrlMeteoGlobaleAck,
        msg-ctrl-meteo-locale-ack                               MsgCtrlMeteoLocaleAck,
        msg-ctrl-checkpoint-save-begin                          MsgCtrlCheckPointSaveBegin,
        msg-ctrl-checkpoint-save-end                            MsgCtrlCheckPointSaveEnd,
        msg-ctrl-checkpoint-load-begin                          MsgCtrlCheckPointLoadBegin,
        msg-ctrl-checkpoint-load-end                            MsgCtrlCheckPointLoadEnd,
        msg-ctrl-checkpoint-set-frequency-ack                   MsgCtrlCheckPointSetFrequencyAck,
        msg-ctrl-checkpoint-save-now-ack                        MsgCtrlCheckPointSaveNowAck,
        msg-ctrl-send-current-state-begin                       MsgCtrlSendCurrentStateBegin,
        msg-ctrl-send-current-state-end                         MsgCtrlSendCurrentStateEnd,

        msg-limit-creation                                      MsgLimitCreation,
        msg-limit-update                                        MsgLimitUpdate,
        msg-limit-destruction                                   MsgLimitDestruction,
        msg-lima-creation                                       MsgLimaCreation,
        msg-lima-update                                         MsgLimaUpdate,
        msg-lima-destruction                                    MsgLimaDestruction, 

        msg-formation-creation                                  MsgFormationCreation,
        msg-knowledge-group-creation                            MsgKnowledgeGroupCreation,
        msg-side-creation                                       MsgSideCreation,

        msg-automate-creation                                   MsgAutomateCreation,
        msg-automate-attributes                                 MsgAutomateAttributes,

        msg-pion-creation                                       MsgPionCreation,
        msg-unit-attributes                                     MsgUnitAttributes,
        msg-unit-pathfind                                       MsgUnitPathFind,                

        msg-change-diplomatie                                   MsgChangeDiplomatie,
        msg-change-automate                                     MsgChangeAutomate,        
        msg-change-liens-logistiques                            MsgChangeLiensLogistiques,

        msg-unit-knowledge-creation                             MsgUnitKnowledgeCreation,
        msg-unit-knowledge-update                               MsgUnitKnowledgeUpdate,
        msg-unit-knowledge-destruction                          MsgUnitKnowledgeDestruction,

        msg-start-pion-fire                                     MsgStartPionFire,
        msg-stop-pion-fire                                      MsgStopPionFire,
        msg-start-population-fire                               MsgStartPopulationFire,
        msg-stop-population-fire                                MsgStopPopulationFire,        
        msg-explosion                                           MsgExplosion,
        msg-start-fire-effect                                   MsgStartFireEffect,
        msg-stop-fire-effect                                    MsgStopFireEffect,

        msg-cr                                                  MsgCR,

        msg-pion-order-management                               MsgPionOrderManagement,
        msg-automate-order-management                           MsgAutomateOrderManagement,
        msg-population-order-management                         MsgPopulationOrderManagement,
        msg-pion-order                                          MsgPionOrder,        
        msg-automate-order                                      MsgAutomateOrder,
        msg-population-order                                    MsgPopulationOrder,

        msg-object-creation                                     MsgObjectCreation,
        msg-object-destruction                                  MsgObjectDestruction,
        msg-object-update                                       MsgObjectUpdate,
        msg-object-knowledge-creation                           MsgObjectKnowledgeCreation,
        msg-object-knowledge-update                             MsgObjectKnowledgeUpdate,
        msg-object-knowledge-destruction                        MsgObjectKnowledgeDestruction,

        msg-log-sante-traitement-humain-creation                MsgLogSanteTraitementHumainCreation,
        msg-log-sante-traitement-humain-update                  MsgLogSanteTraitementHumainUpdate,
        msg-log-sante-traitement-humain-destruction             MsgLogSanteTraitementHumainDestruction,
        msg-log-sante-etat                                      MsgLogSanteEtat,

        msg-log-maintenance-traitement-equipement-creation      MsgLogMaintenanceTraitementEquipementCreation,
        msg-log-maintenance-traitement-equipement-update        MsgLogMaintenanceTraitementEquipementUpdate,
        msg-log-maintenance-traitement-equipement-destruction   MsgLogMaintenanceTraitementEquipementDestruction,
        msg-log-maintenance-etat                                MsgLogMaintenanceEtat,

        msg-log-ravitaillement-traitement-creation              MsgLogRavitaillementTraitementCreation,
        msg-log-ravitaillement-traitement-update                MsgLogRavitaillementTraitementUpdate,
        msg-log-ravitaillement-traitement-destruction           MsgLogRavitaillementTraitementDestruction,
        msg-log-ravitaillement-etat                             MsgLogRavitaillementEtat,
        msg-log-ravitaillement-quotas                           MsgLogRavitaillementQuotas,  

        msg-population-creation                                 MsgPopulationCreation,
        msg-population-update                                   MsgPopulationUpdate,
        msg-population-concentration-creation                   MsgPopulationConcentrationCreation,
        msg-population-concentration-destruction                MsgPopulationConcentrationDestruction,
        msg-population-concentration-update                     MsgPopulationConcentrationUpdate,
        msg-population-flux-creation                            MsgPopulationFluxCreation,
        msg-population-flux-destruction                         MsgPopulationFluxDestruction,
        msg-population-flux-update                              MsgPopulationFluxUpdate,

        msg-population-knowledge-creation                       MsgPopulationKnowledgeCreation,
        msg-population-knowledge-update                         MsgPopulationKnowledgeUpdate,
        msg-population-knowledge-destruction                    MsgPopulationKnowledgeDestruction,
        msg-population-concentration-knowledge-creation         MsgPopulationConcentrationKnowledgeCreation,
        msg-population-concentration-knowledge-destruction      MsgPopulationConcentrationKnowledgeDestruction,
        msg-population-concentration-knowledge-update           MsgPopulationConcentrationKnowledgeUpdate,
        msg-population-flux-knowledge-creation                  MsgPopulationFluxKnowledgeCreation,
        msg-population-flux-knowledge-destruction               MsgPopulationFluxKnowledgeDestruction,
        msg-population-flux-knowledge-update                    MsgPopulationFluxKnowledgeUpdate
    }    
}

MsgsInSim ::= SEQUENCE
{
    context INTEGER DEFAULT 0,
    msg     CHOICE
    {
        msg-ctrl-client-announcement            MsgCtrlClientAnnouncement,
        msg-ctrl-stop                           MsgCtrlStop,
        msg-ctrl-pause                          MsgCtrlPause,
        msg-ctrl-resume                         MsgCtrlResume,
        msg-ctrl-change-time-factor             MsgCtrlChangeTimeFactor,      
        msg-ctrl-meteo-globale                  MsgCtrlMeteoGlobale,
        msg-ctrl-meteo-locale                   MsgCtrlMeteoLocale,
        msg-ctrl-checkpoint-save-now            MsgCtrlCheckPointSaveNow,
        msg-ctrl-checkpoint-set-frequency       MsgCtrlCheckPointSetFrequency, 

        msg-limit-creation-request              MsgLimitCreationRequest,
        msg-limit-destruction-request           MsgLimitDestructionRequest,
        msg-limit-update-request                MsgLimitUpdateRequest,
        msg-lima-creation-request               MsgLimaCreationRequest,
        msg-lima-destruction-request            MsgLimaDestruction,
        msg-lima-update-request                 MsgLimaUpdateRequest,

        msg-pion-order                          MsgPionOrder,
        msg-automate-order                      MsgAutomateOrder,
        msg-population-order                    MsgPopulationOrder,
        msg-frag-order                          MsgFragOrder,

        msg-set-automate-mode                   MsgSetAutomateMode,

        msg-unit-magic-action                   MsgUnitMagicAction,
        msg-object-magic-action                 MsgObjectMagicAction,
        msg-population-magic-action             MsgPopulationMagicAction,

        msg-change-diplomatie                   MsgChangeDiplomatie,
        msg-change-groupe-connaissance          MsgChangeGroupeConnaissance,
        msg-change-liens-logistiques            MsgChangeLiensLogistiques,
        msg-change-automate                     MsgChangeAutomate,

        msg-log-ravitaillement-pousser-flux     MsgLogRavitaillementPousserFlux,
        msg-log-ravitaillement-change-quotas    MsgLogRavitaillementChangeQuotas
    }
}

--
-- 
--  
MsgsInClient ::= SEQUENCE
{
    context INTEGER DEFAULT 0,
    msg     CHOICE
    {
        -- ACKS
        msg-limit-creation-request-ack                          MsgLimitCreationRequestAck,
        msg-limit-destruction-request-ack                       MsgLimitDestructionRequestAck,
        msg-limit-update-request-ack                            MsgLimitUpdateRequestAck,
        msg-lima-creation-request-ack                           MsgLimaCreationRequestAck,
        msg-lima-destruction-request-ack                        MsgLimaDestructionRequestAck,
        msg-lima-update-request-ack                             MsgLimaUpdateRequestAck,

        msg-pion-order-ack                                      MsgPionOrderAck,
        msg-automate-order-ack                                  MsgAutomateOrderAck,
        msg-population-order-ack                                MsgPopulationOrderAck,
        msg-frag-order-ack                                      MsgFragOrderAck,                                                                
        msg-set-automate-mode-ack                               MsgSetAutomateModeAck,
                                                                
        msg-unit-magic-action-ack                               MsgUnitMagicActionAck,
        msg-object-magic-action-ack                             MsgObjectMagicActionAck,
        msg-population-magic-action-ack                         MsgPopulationMagicActionAck,
       
        msg-change-diplomatie-ack                               MsgChangeDiplomatieAck,
        msg-change-groupe-connaissance-ack                      MsgChangeGroupeConnaissanceAck,
        msg-change-liens-logistiques-ack                        MsgChangeLiensLogistiquesAck,
        msg-change-liens-logistiques                            MsgChangeLiensLogistiques,
        msg-change-automate-ack                                 MsgChangeAutomateAck,   
        
        msg-log-ravitaillement-pousser-flux-ack                 MsgLogRavitaillementPousserFluxAck,
        msg-log-ravitaillement-change-quotas-ack                MsgLogRavitaillementChangeQuotasAck,   

        -- MESSAGES
        msg-ctrl-info                                           MsgCtrlInfo,
        msg-ctrl-begin-tick                                     MsgCtrlBeginTick,
        msg-ctrl-end-tick                                       MsgCtrlEndTick,
        msg-ctrl-stop-ack                                       MsgCtrlStopAck,
        msg-ctrl-pause-ack                                      MsgCtrlPauseAck,
        msg-ctrl-resume-ack                                     MsgCtrlResumeAck,
        msg-ctrl-change-time-factor-ack                         MsgCtrlChangeTimeFactorAck,
        msg-ctrl-meteo-globale-ack                              MsgCtrlMeteoGlobaleAck,
        msg-ctrl-meteo-locale-ack                               MsgCtrlMeteoLocaleAck,
        msg-ctrl-checkpoint-save-begin                          MsgCtrlCheckPointSaveBegin,
        msg-ctrl-checkpoint-save-end                            MsgCtrlCheckPointSaveEnd,
        msg-ctrl-checkpoint-load-begin                          MsgCtrlCheckPointLoadBegin,
        msg-ctrl-checkpoint-load-end                            MsgCtrlCheckPointLoadEnd,
        msg-ctrl-checkpoint-set-frequency-ack                   MsgCtrlCheckPointSetFrequencyAck,
        msg-ctrl-checkpoint-save-now-ack                        MsgCtrlCheckPointSaveNowAck,
        msg-ctrl-send-current-state-begin                       MsgCtrlSendCurrentStateBegin,
        msg-ctrl-send-current-state-end                         MsgCtrlSendCurrentStateEnd,

        msg-auth-login-ack                                      MsgAuthLoginAck,
        msg-profile-creation                                    MsgProfileCreation,
        msg-profile-creation-request-ack                        MsgProfileCreationRequestAck,
        msg-profile-update                                      MsgProfileUpdate,
        msg-profile-update-request-ack                          MsgProfileUpdateRequestAck,
        msg-profile-destruction                                 MsgProfileDestruction,
        msg-profile-destruction-request-ack                     MsgProfileDestructionRequestAck,

        msg-limit-creation                                      MsgLimitCreation,
        msg-limit-update                                        MsgLimitUpdate,
        msg-limit-destruction                                   MsgLimitDestruction,
        msg-lima-creation                                       MsgLimaCreation,
        msg-lima-update                                         MsgLimaUpdate,
        msg-lima-destruction                                    MsgLimaDestruction, 
        
        msg-formation-creation                                  MsgFormationCreation,
        msg-knowledge-group-creation                            MsgKnowledgeGroupCreation,
        msg-side-creation                                       MsgSideCreation,
                
        msg-automate-creation                                   MsgAutomateCreation,
        msg-automate-attributes                                 MsgAutomateAttributes,        
        
        msg-pion-creation                                       MsgPionCreation,
        msg-unit-attributes                                     MsgUnitAttributes,
        msg-unit-pathfind                                       MsgUnitPathFind,
                
        msg-change-diplomatie                                   MsgChangeDiplomatie,

        msg-unit-knowledge-creation                             MsgUnitKnowledgeCreation,
        msg-unit-knowledge-update                               MsgUnitKnowledgeUpdate,
        msg-unit-knowledge-destruction                          MsgUnitKnowledgeDestruction,

        msg-start-pion-fire                                     MsgStartPionFire,
        msg-stop-pion-fire                                      MsgStopPionFire,
        msg-start-population-fire                               MsgStartPopulationFire,
        msg-stop-population-fire                                MsgStopPopulationFire,        
        msg-explosion                                           MsgExplosion,
        msg-start-fire-effect                                   MsgStartFireEffect,
        msg-stop-fire-effect                                    MsgStopFireEffect,
        
        msg-cr                                                  MsgCR,

        msg-pion-order-management                               MsgPionOrderManagement,
        msg-automate-order-management                           MsgAutomateOrderManagement,
        msg-population-order-management                         MsgPopulationOrderManagement,
        msg-pion-order                                          MsgPionOrder,
        msg-automate-order                                      MsgAutomateOrder,
        msg-population-order                                    MsgPopulationOrder,

        msg-object-creation                                     MsgObjectCreation,
        msg-object-destruction                                  MsgObjectDestruction,
        msg-object-update                                       MsgObjectUpdate,
        msg-object-knowledge-creation                           MsgObjectKnowledgeCreation,
        msg-object-knowledge-update                             MsgObjectKnowledgeUpdate,
        msg-object-knowledge-destruction                        MsgObjectKnowledgeDestruction,
        
        msg-change-automate                                     MsgChangeAutomate,
           
        msg-log-sante-traitement-humain-creation                MsgLogSanteTraitementHumainCreation,
        msg-log-sante-traitement-humain-update                  MsgLogSanteTraitementHumainUpdate,
        msg-log-sante-traitement-humain-destruction             MsgLogSanteTraitementHumainDestruction,
        msg-log-sante-etat                                      MsgLogSanteEtat,
        
        msg-log-maintenance-traitement-equipement-creation      MsgLogMaintenanceTraitementEquipementCreation,
        msg-log-maintenance-traitement-equipement-update        MsgLogMaintenanceTraitementEquipementUpdate,
        msg-log-maintenance-traitement-equipement-destruction   MsgLogMaintenanceTraitementEquipementDestruction,
        msg-log-maintenance-etat                                MsgLogMaintenanceEtat,
        
        msg-log-ravitaillement-traitement-creation              MsgLogRavitaillementTraitementCreation,
        msg-log-ravitaillement-traitement-update                MsgLogRavitaillementTraitementUpdate,
        msg-log-ravitaillement-traitement-destruction           MsgLogRavitaillementTraitementDestruction,
        msg-log-ravitaillement-etat                             MsgLogRavitaillementEtat,
        msg-log-ravitaillement-quotas                           MsgLogRavitaillementQuotas,  
        
        msg-population-creation                                 MsgPopulationCreation,
        msg-population-update                                   MsgPopulationUpdate,
        msg-population-concentration-creation                   MsgPopulationConcentrationCreation,
        msg-population-concentration-destruction                MsgPopulationConcentrationDestruction,
        msg-population-concentration-update                     MsgPopulationConcentrationUpdate,
        msg-population-flux-creation                            MsgPopulationFluxCreation,
        msg-population-flux-destruction                         MsgPopulationFluxDestruction,
        msg-population-flux-update                              MsgPopulationFluxUpdate,
        
        msg-population-knowledge-creation                       MsgPopulationKnowledgeCreation,
        msg-population-knowledge-update                         MsgPopulationKnowledgeUpdate,
        msg-population-knowledge-destruction                    MsgPopulationKnowledgeDestruction,
        msg-population-concentration-knowledge-creation         MsgPopulationConcentrationKnowledgeCreation,
        msg-population-concentration-knowledge-destruction      MsgPopulationConcentrationKnowledgeDestruction,
        msg-population-concentration-knowledge-update           MsgPopulationConcentrationKnowledgeUpdate,
        msg-population-flux-knowledge-creation                  MsgPopulationFluxKnowledgeCreation,
        msg-population-flux-knowledge-destruction               MsgPopulationFluxKnowledgeDestruction,
        msg-population-flux-knowledge-update                    MsgPopulationFluxKnowledgeUpdate
    }    
}

MsgsOutClient ::= SEQUENCE
{
    context INTEGER DEFAULT 0,
    msg     CHOICE
    {
        msg-ctrl-stop                           MsgCtrlStop,
        msg-ctrl-pause                          MsgCtrlPause,
        msg-ctrl-resume                         MsgCtrlResume,
        msg-ctrl-change-time-factor             MsgCtrlChangeTimeFactor,      
        msg-ctrl-meteo-globale                  MsgCtrlMeteoGlobale,
        msg-ctrl-meteo-locale                   MsgCtrlMeteoLocale,
        msg-ctrl-checkpoint-save-now            MsgCtrlCheckPointSaveNow,
        msg-ctrl-checkpoint-set-frequency       MsgCtrlCheckPointSetFrequency, 
        
        msg-auth-login                          MsgAuthLogin,
        msg-profile-creation-request            MsgProfileCreationRequest,
        msg-profile-update-request              MsgProfileUpdateRequest,
        msg-profile-destruction-request         MsgProfileDestructionRequest,

        msg-limit-creation-request              MsgLimitCreationRequest,
        msg-limit-destruction-request           MsgLimitDestructionRequest,
        msg-limit-update-request                MsgLimitUpdateRequest,
        msg-lima-creation-request               MsgLimaCreationRequest,
        msg-lima-destruction-request            MsgLimaDestruction,
        msg-lima-update-request                 MsgLimaUpdateRequest,
                                                        
        msg-pion-order                          MsgPionOrder,
        msg-automate-order                      MsgAutomateOrder,
        msg-population-order                    MsgPopulationOrder,
        msg-frag-order                          MsgFragOrder,
                                                
        msg-set-automate-mode                   MsgSetAutomateMode,
                                                
        msg-unit-magic-action                   MsgUnitMagicAction,
        msg-object-magic-action                 MsgObjectMagicAction,
        msg-population-magic-action             MsgPopulationMagicAction,

        msg-change-diplomatie                   MsgChangeDiplomatie,
        msg-change-groupe-connaissance          MsgChangeGroupeConnaissance,
        msg-change-liens-logistiques            MsgChangeLiensLogistiques,
        msg-change-automate                     MsgChangeAutomate,
        
        msg-log-ravitaillement-pousser-flux     MsgLogRavitaillementPousserFlux,
        msg-log-ravitaillement-change-quotas    MsgLogRavitaillementChangeQuotas
    }
}

END
