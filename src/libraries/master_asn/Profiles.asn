--
-- file name : Profiles.asn
--
-- Profiles messages
--

Profiles DEFINITIONS AUTOMATIC TAGS ::= BEGIN

-- BEGIN includes
ProfilesIncludes ::= SEQUENCE {}
ProfilesExports  ::= NULL
-- END includes

Profile ::= SEQUENCE
{
    login               VisibleString,
    role-adaptation     BOOLEAN,
    role-preparation    BOOLEAN,
    role-game           BOOLEAN,
    role-supervision    BOOLEAN
}

MsgAuthenticationRequest ::= SEQUENCE
{
    login    VisibleString,
    password VisibleString
}

MsgAuthenticationResponse ::= SEQUENCE
{
    return-code ENUMERATED
    {
        ok,
        invalid-login
    },
    profile Profile OPTIONAL
}

END
