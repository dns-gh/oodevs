--
-- file name : Exercises.asn
--
-- Exercises messages
--

Exercises DEFINITIONS ::= BEGIN

-- BEGIN includes
ExercisesIncludes ::= SEQUENCE {}
ExercisesExports  ::= NULL
-- END includes

Exercise ::= SEQUENCE
{
    name     VisibleString,
    terrain  VisibleString,
    dataset  VisibleString,
    physical VisibleString
}

MsgExerciseCreation    ::= Exercise
MsgExerciseUpdate      ::= Exercise
MsgExerciseDestruction ::= VisibleString

MsgExerciseCreationRequest    ::= Exercise
MsgExerciseCreationRequestAck ::= SEQUENCE
{
    return-code ENUMERATED
    {
        success,
        forbidden,
        invalid-name
    },
    name VisibleString
}

MsgExerciseUpdateRequest    ::= SEQUENCE
{
    exercise Exercise,
    name     VisibleString
}

MsgExerciseUpdateRequestAck ::= SEQUENCE
{
    return-code ENUMERATED
    {
        success,
        forbidden,
        not-found,
        invalid-name
    },
    name VisibleString
}

MsgExerciseDestructionRequest    ::= VisibleString
MsgExerciseDestructionRequestAck ::= SEQUENCE
{
    return-code ENUMERATED
    {
        success,
        forbidden,
        not-found
        
    },
    name VisibleString
}

END
