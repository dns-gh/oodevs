--
-- file name : AarMessages.asn
--
-- After Action Review messages list
--

AarMessages DEFINITIONS AUTOMATIC TAGS ::= BEGIN

-- BEGIN includes
IMPORTS AarExports FROM Aar;

AarMessagesIncludes ::= SEQUENCE
{ AarExports }
AarMessagesExports  ::= NULL
-- END includes


-- 
-- 
-- 
MsgsAarToClient ::= SEQUENCE
{
    context INTEGER DEFAULT 0,
    msg     CHOICE
    {
        msg-aar-information             MsgAarInformation,
        msg-plot-result                 MsgPlotResult,
        msg-indicator                   MsgIndicator
    }
}

MsgsClientToAar ::= SEQUENCE
{
    context INTEGER DEFAULT 0,
    msg     CHOICE
    {
        msg-plot-request                MsgPlotRequest
    }
}

END
