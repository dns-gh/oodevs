--
-- file name : Control.asn
--
-- Messages de controle de la sim
--

Control DEFINITIONS AUTOMATIC TAGS ::= BEGIN

-- BEGIN includes
IMPORTS BaseExports FROM Base;
ControlIncludes ::= SEQUENCE { BaseExports }
ControlExports  ::= NULL
-- END includes

-- Definition de tous les messages de controle (MOS->SIM et SIM->MOS)
EnumControlErrorCode ::= ENUMERATED
{
   no-error                     (0),
   error-already-started        (1),
   error-not-started            (2),
   error-not-paused             (3),
   error-already-paused         (4),
   error-invalid-time-factor    (5),
   error-invalid-date-time      (6)
}

MsgControlStop     ::= NULL 
MsgControlStopAck  ::= EnumControlErrorCode

MsgControlPause    ::= NULL
MsgControlPauseAck ::= EnumControlErrorCode

MsgControlResume    ::= NULL
MsgControlResumeAck ::= EnumControlErrorCode

MsgControlSkipToTick    ::= INTEGER
MsgControlSkipToTickAck ::= SEQUENCE
{
    tick        INTEGER,
    error-code  EnumControlErrorCode
}

MsgControlToggleVisionCones ::= BOOLEAN

MsgControlChangeTimeFactor    ::= INTEGER
MsgControlChangeTimeFactorAck ::= SEQUENCE
{
    time-factor INTEGER,
    error-code  EnumControlErrorCode
}

MsgControlBeginTick ::= SEQUENCE
{
    current-tick        INTEGER,
    date-time           DateTime
}

MsgControlEndTick   ::= SEQUENCE
{
    current-tick        INTEGER,
    tick-duration       INTEGER,    -- En millisecondes
    long-pathfinds      INTEGER,
    short-pathfinds     INTEGER,
    memory              INTEGER,
    virtual-memory      INTEGER
}

MsgControlClientAnnouncement ::= NULL

EnumSimulationState ::= ENUMERATED
{
    running (0),
    paused  (1),
    stopped (2)
}

MsgControlInformation ::= SEQUENCE
{
    current-tick            INTEGER,
    initial-date-time       DateTime,
    date-time               DateTime,
    tick-duration           INTEGER,  -- En secondes
    time-factor             INTEGER,
    checkpoint-frequency    INTEGER, -- En minutes
    status                  EnumSimulationState,
    send-vision-cones       BOOLEAN, -- No comment ...
    profiling-enabled       BOOLEAN
}

MsgControlReplayInformation ::= SEQUENCE
{
    current-tick            INTEGER,     
    initial-date-time       DateTime,
    date-time               DateTime,
    tick-duration           INTEGER,  -- En secondes
    time-factor             INTEGER,
    status                  EnumSimulationState,
    tick-count              INTEGER
}

MsgControlProfilingInformation ::= SEQUENCE
{
    perception              REAL, 
    decision                REAL,
    action                  REAL,
    main-loop               REAL
}

----------------
-- SAUVEGARDES
----------------

-- SIM -> MOS
MsgControlCheckPointSaveBegin ::= NULL
MsgControlCheckPointSaveEnd   ::= SEQUENCE
{
    name VisibleString 
}
MsgControlCheckPointLoadBegin ::= NULL
MsgControlCheckPointLoadEnd   ::= NULL

-- MOS -> SIM
MsgControlCheckPointSetFrequency    ::= INTEGER -- En minutes
MsgControlCheckPointSetFrequencyAck ::= NULL
MsgControlCheckPointSaveNow         ::= SEQUENCE
{
    name VisibleString OPTIONAL    
}
MsgControlCheckPointSaveNowAck      ::= NULL

-- SIM -> MOS
MsgControlSendCurrentStateBegin    ::= NULL
MsgControlSendCurrentStateEnd      ::= NULL
                                         
----------------
-- METEO
----------------

EnumPrecipitationType ::= ENUMERATED
{
    pas-de-precipitation(0),
    tempete-sable       (1),
    brouillard          (2),
    crachin             (3),
    pluie               (4),
    neige               (5)
}

MeteoAttributes ::= SEQUENCE
{
    temperature                         INTEGER,
    wind-speed                          Speed, -- en km/h
    wind-direction                      Heading,
    cloud-floor                         Elevation,
    cloud-ceiling                       Elevation,
    cloud-density                       Percentage,
    precipitation                       EnumPrecipitationType
}

MsgControlGlobalMeteo ::= SEQUENCE
{
    attributes MeteoAttributes
}

MsgControlLocalMeteo ::= SEQUENCE
{
    top-left-coordinate      CoordLatLong,
    bottom-right-coordinate  CoordLatLong,
    meteo CHOICE
    {
        attributes MeteoAttributes,
        global     NULL
    }
}

MsgControlGlobalMeteoAck ::= NULL
MsgControlLocalMeteoAck  ::= NULL

----------------
-- DATETIME
----------------

MsgControlDatetimeChange ::= SEQUENCE
{
    date-time DateTime
}

MsgControlDatetimeChangeAck ::= EnumControlErrorCode

END -- Control
