--
-- file name : Base.asn
--
-- Types de base
--

Base DEFINITIONS AUTOMATIC TAGS ::= BEGIN

-- BEGIN includes
-- IMPORTS BaseExports FROM Base;
BaseIncludes ::= SEQUENCE {}
BaseExports  ::= NULL
-- END includes


--
-- Géométrie
--
EnumLocationType ::= ENUMERATED
{ 
    circle   (0), -- Circle
    ellipse  (1), -- Ellipse
    line     (2), -- Line 
    polygon  (3), -- Polygon
    point    (4), -- Point
    sector   (5)  -- Sector
}

CoordLatLong ::= SEQUENCE
{
    latitude  REAL,
    longitude REAL
}

ColorRGBA ::= SEQUENCE
{
	red INTEGER,
	green INTEGER,
	blue INTEGER,
	alpha REAL
}

CoordLatLongList ::= SEQUENCE OF CoordLatLong

Location ::= SEQUENCE 
{
    type          EnumLocationType,
    coordinates   CoordLatLongList
}

Point      ::= Location (WITH COMPONENTS {...,type(point)})
Line       ::= Location (WITH COMPONENTS {...,type(line)})
Path       ::= Location (WITH COMPONENTS {...,type(line)})
Polygon    ::= Location (WITH COMPONENTS {...,type(polygon)})
Segment    ::= Location (WITH COMPONENTS {type(line)   , coordinates (SIZE(2))})
Circle     ::= Location (WITH COMPONENTS {type(circle) , coordinates (SIZE(2))}) -- Format : centre, point sur le cercle
Ellipse    ::= Location (WITH COMPONENTS {type(ellipse), coordinates (SIZE(3))}) -- Format : centre, point petit axe, point grand axe
Sector     ::= Location (WITH COMPONENTS {type(sector) , coordinates (SIZE(3))}) -- Format : centre, point 1, point 2 dans le sens trigo

LocationList ::= SEQUENCE OF Location
PolygonList  ::= SEQUENCE OF Polygon
PathList     ::= SEQUENCE OF Path
PointList    ::= SEQUENCE OF Point

--
-- Types
--
OID                     ::= INTEGER
ListOID                 ::= SEQUENCE OF OID
UnitFire                ::= OID
PopulationFire          ::= OID
Unit                    ::= OID
Automat                 ::= OID
Population              ::= OID
Team                    ::= OID
Formation               ::= OID
UrbanBlock              ::= OID
KnowledgeGroup          ::= OID
UnitKnowledge           ::= OID
ObjectKnowledge         ::= OID
UrbanKnowledge          ::= OID
PopulationKnowledge     ::= OID
AutomatList             ::= SEQUENCE OF Automat 
UnitList                ::= SEQUENCE OF Unit
UnitKnowledgeList       ::= SEQUENCE OF UnitKnowledge
ObjectKnowledgeList     ::= SEQUENCE OF ObjectKnowledge
TeamList                ::= SEQUENCE OF Team
PopulationList          ::= SEQUENCE OF Population
FormationList           ::= SEQUENCE OF Formation
EquipmentType           ::= OID
DotationType            ::= OID
BreakdownType           ::= OID
UnitType                ::= OID
AutomatType             ::= OID
PopulationType          ::= OID
KnowledgeGroupType      ::= VisibleString -- LTO
Percentage              ::= INTEGER(0..100)
FreePercentage          ::= INTEGER
Height                  ::= INTEGER
Elevation               ::= INTEGER
Speed                   ::= INTEGER
Heading                 ::= INTEGER(0..360)
DateTime                ::= OCTET STRING (SIZE(15)) -- YYYYMMDDTHHMMSS


EnumDotationFamily ::= ENUMERATED
{
    munition (0),
    carburant(1),
    explosif (2),
    mine     (3),
    barbele  (4),
    piece    (5),
    ration   (6)
}

EnumAmmunitionFamily ::= ENUMERATED
{
    obus        (0),
    missile-air (1),
    missile-sol (2),
    mitraille   (3)
}

EnumUnitIdentificationLevel ::= ENUMERATED
{
    identifiee (0),
    reconnue   (1),
    detectee   (2),
    signale    (3) 
}

-- $$$$ Merge with above
EnumUnitVisibility ::= ENUMERATED
{
    invisible  (0),
    detected   (1),
    recognized (2),
    identified (3),
    recorded   (4)
}


EnumNatureLevel ::= ENUMERATED
{
    none        (0),  -- None
    o           (1),  -- Team
    oo          (2),  -- Group/Patrol/Squad
    ooo         (3),  -- Section/platoon
    i           (4),  -- Company
    ii          (5),  -- Battalion
    iii         (6),  -- Regiment
    x           (7),  -- Brigade
    xx          (8),  -- Division
    xxx         (9),  -- Army corps
    xxxx        (10), -- Field army (obsolete)
    xxxxx       (11)  -- Army group/front (obsolete)
}

AtlasNature ::= BIT STRING 
{ 
    blinde          (0), 
    ass             (1), 
    pc              (2), 
    log             (3), 
    mortier         (4), 
    lance-roquette  (5), 
    vehicule        (6), 
    personnel-a-pied(7), 
    helicoptere     (8), 
    indefini        (9), 
    asa             (10),
    none            (11) 
}

EnumHumanWound ::= ENUMERATED 
{
    non-blesse            (0),
    mort                  (1),
    blesse-urgence-1      (2),
    blesse-urgence-2      (3),
    blesse-urgence-3      (4),
    blesse-urgence-extreme(5)
}

EnumHumanRank ::= ENUMERATED
{
    officier    (0),
    sous-officer(1),
    mdr         (2)
}

EnumChangeHierarchyErrorCode ::= ENUMERATED
{
    no-error                             (0),
    error-invalid-pion                   (1),
    error-invalid-automate               (2),
    error-invalid-formation              (3),
    error-invalid-automate-tc2           (4),
    error-invalid-automate-maintenance   (5),
    error-invalid-automate-sante         (6),
    error-invalid-automate-ravitaillement(7),
    error-unit-surrendered               (8),    
    error-invalid-camp                   (9),
    error-invalid-groupe-connaissance    (10),
    error-camps-incompatibles            (11)
}                  

END -- Base
