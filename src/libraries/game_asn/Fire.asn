--
-- file name : Fire.asn
--
-- Messages de gestion des tirs
--

Fire DEFINITIONS AUTOMATIC TAGS ::= BEGIN

-- BEGIN includes
IMPORTS BaseExports FROM Base;
FireIncludes ::= SEQUENCE { BaseExports }
FireExports  ::= NULL
-- END includes

UnitHumanFireDamage ::= SEQUENCE
{
    rank                        EnumHumanRank,
    alive-nbr                   INTEGER, -- NB : toutes les valeurs peuvent être négatives
    dead-nbr                    INTEGER,
    wounded-u1-nbr              INTEGER,
    wounded-u2-nbr              INTEGER,
    wounded-u3-nbr              INTEGER,
    wounded-ue-nbr              INTEGER
}

UnitEquipmentFireDamage ::= SEQUENCE
{
    equipement-type  EquipmentType,
    available-nbr    INTEGER,
    unavailable-nbr  INTEGER,
    repairable-nbr   INTEGER
}

UnitFireDamages ::= SEQUENCE
{
    target     Unit,
    humans     SEQUENCE OF UnitHumanFireDamage,
    equipments SEQUENCE OF UnitEquipmentFireDamage
}

PopulationFireDamages ::= SEQUENCE
{
    target    Population,
    dead-nbr  INTEGER
}

UnitsFireDamages       ::= SEQUENCE OF UnitFireDamages
PopulationsFireDamages ::= SEQUENCE OF PopulationFireDamages

-- Tir pion
MsgStartUnitFire ::= SEQUENCE
{
    fire-oid     UnitFire,
    firer-oid    Unit,
    target      CHOICE
    {
        unit       Unit,
        population Population,
        position   CoordLatLong
    },
    type        ENUMERATED
    {
        direct,
        indirect
    },
    ammunition    DotationType OPTIONAL
}

MsgStopUnitFire ::= SEQUENCE
{
    fire-oid             UnitFire,
    units-damages       UnitsFireDamages,
    populations-damages PopulationsFireDamages
}

-- Tir population
MsgStartPopulationFire ::= SEQUENCE
{
    fire-oid     PopulationFire,
    firer-oid    Population
}

MsgStopPopulationFire ::= SEQUENCE
{
    fire-oid       PopulationFire,
    units-damages UnitsFireDamages
}

-- Explosion mine
MsgExplosion ::= SEQUENCE
{
    object-oid           OID,
    units-damages       UnitsFireDamages,
    populations-damages PopulationsFireDamages
}

-- Effets de tirs
EnumFireEffectType ::= ENUMERATED
{
    fumigene    (0),
    eclairant   (1)
}

MsgStartFireEffect ::= SEQUENCE
{
    effect-oid   OID,
    location    Location,
    type        EnumFireEffectType
}

MsgStopFireEffect ::= OID


END -- Fire
