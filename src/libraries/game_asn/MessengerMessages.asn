--
-- file name : SimMessages.asn
--
-- Liste des messages
--

MessengerMessages DEFINITIONS AUTOMATIC TAGS ::= BEGIN

-- BEGIN includes
IMPORTS BaseExports                   FROM Base
        LimaLimiteExports             FROM LimaLimite
        IntelligenceExports           FROM Intelligence
        DrawingExports                FROM Drawing
        ChatExports                   FROM Chat
        NotesExports				  FROM Notes;

MessengerMessagesIncludes ::= SEQUENCE
{ BaseExports, LimaLimiteExports, IntelligenceExports, DrawingExports, ChatExports,NotesExports }
MessengerMessagesExports  ::= NULL
-- END includes


--
--
--
MsgsMessengerToClient ::= CHOICE
{
    -- LIMIT
    msg-limit-creation                                      MsgLimitCreation,
    msg-limit-update                                        MsgLimitUpdate,
    msg-limit-destruction                                   MsgLimitDestruction,

    msg-limit-creation-request-ack                          MsgLimitCreationRequestAck,
    msg-limit-destruction-request-ack                       MsgLimitDestructionRequestAck,
    msg-limit-update-request-ack                            MsgLimitUpdateRequestAck,

    -- LIMA 
    msg-lima-creation                                       MsgLimaCreation,
    msg-lima-update                                         MsgLimaUpdate,
    msg-lima-destruction                                    MsgLimaDestruction,

    msg-lima-creation-request-ack                           MsgLimaCreationRequestAck,
    msg-lima-destruction-request-ack                        MsgLimaDestructionRequestAck,
    msg-lima-update-request-ack                             MsgLimaUpdateRequestAck,

  -- INTELLIGENCE
    msg-intelligence-creation                               MsgIntelligenceCreation,
    msg-intelligence-update                                 MsgIntelligenceUpdate,
    msg-intelligence-destruction                            MsgIntelligenceDestruction,

    msg-intelligence-creation-request-ack                   MsgIntelligenceCreationRequestAck,
    msg-intelligence-update-request-ack                     MsgIntelligenceUpdateRequestAck,
    msg-intelligence-destruction-request-ack                MsgIntelligenceDestructionRequestAck,

    -- SHAPE 
    msg-shape-creation                                       MsgShapeCreation,
    msg-shape-update                                         MsgShapeUpdate,
    msg-shape-destruction                                    MsgShapeDestruction,

    msg-shape-creation-request-ack                           MsgShapeCreationRequestAck,
    msg-shape-destruction-request-ack                        MsgShapeDestructionRequestAck,
    msg-shape-update-request-ack                             MsgShapeUpdateRequestAck,

    -- NOTE 
    msg-note-creation                                        MsgNoteCreation,
    msg-note-update                                          MsgNoteUpdate,
    msg-note-destruction                                     MsgNoteDestruction,
    
    msg-text-message                                         MsgTextMessage
}

MsgsClientToMessenger ::= CHOICE
{

    msg-limit-creation-request              MsgLimitCreationRequest,
    msg-limit-destruction-request           MsgLimitDestructionRequest,
    msg-limit-update-request                MsgLimitUpdateRequest,

    msg-lima-creation-request               MsgLimaCreationRequest,
    msg-lima-destruction-request            MsgLimaDestructionRequest,
    msg-lima-update-request                 MsgLimaUpdateRequest,

    msg-intelligence-creation-request       MsgIntelligenceCreationRequest,
    msg-intelligence-update-request         MsgIntelligenceUpdateRequest,
    msg-intelligence-destruction-request    MsgIntelligenceDestructionRequest,

    msg-shape-creation-request              MsgShapeCreationRequest,
    msg-shape-destruction-request           MsgShapeDestructionRequest,
    msg-shape-update-request                MsgShapeUpdateRequest,

    msg-note-creation-request               MsgNoteCreationRequest,
    msg-note-destruction-request            MsgNoteDestructionRequest,
    msg-note-update-request                 MsgNoteUpdateRequest,
      
    msg-text-message                        MsgTextMessage
}

END
