--
-- file name : Aar.asn
--
-- Messages de gestion des attributs d'une unité
--

Aar DEFINITIONS AUTOMATIC TAGS ::= BEGIN

-- BEGIN includes
IMPORTS BaseExports FROM Base;
AarIncludes ::= SEQUENCE { BaseExports }
AarExports  ::= NULL
-- END includes

MsgAarInformation ::= SEQUENCE
{
    information VisibleString -- $$$$ XmlOverAsn pattern
}

MsgIndicator ::= SEQUENCE
{
    name VisibleString,
    value REAL
}

MsgPlotResult ::= SEQUENCE
{
    identifier INTEGER,      -- $$$$ Context
    error VisibleString, 
    values SEQUENCE OF REAL
}

MsgPlotRequest ::= SEQUENCE
{
    identifier INTEGER,    -- $$$$ Context 
    request VisibleString  -- $$$$ XmlOverAsn pattern again
}


END -- Aar
