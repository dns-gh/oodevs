--
-- file name : Object.asn
--
-- Messages de gestion des objets
--

Object DEFINITIONS AUTOMATIC TAGS ::= BEGIN

-- BEGIN includes
IMPORTS BaseExports FROM Base;
ObjectIncludes ::= SEQUENCE { BaseExports }
ObjectExports  ::= NULL
-- END includes


EnumDemolitionTargetType ::= ENUMERATED
{
    preliminary     (0),
    reserved        (1)
}

EnumObjectErrorCode ::= ENUMERATED
{
    no-error                         (0),
    error-invalid-object             (1),
    error-invalid-id                 (2),
    error-invalid-camp               (3),
    error-invalid-localisation       (4),
    error-missing-specific-attributes(5),
    error-invalid-specific-attributes(6)
}

ObjectAttributeBypass ::= SEQUENCE
{
    percentage      INTEGER( 0..100 )  OPTIONAL
}

ObjectAttributeConstruction ::= SEQUENCE
{
    dotation-type   DotationType        OPTIONAL,
    dotation-nbr    INTEGER             OPTIONAL,
    density         REAL                OPTIONAL,
    percentage      INTEGER( 0..100 )   OPTIONAL
}

ObjectAttributeLogistic ::= SEQUENCE
{
    tc2             Automat
}

ObjectAttributeInteractionHeight ::= SEQUENCE
{
    height        REAL
}

LocatedQuantity ::= SEQUENCE
{    
    coordinate    CoordLatLong,
    quantity      REAL
}

LocatedQuantityList ::= SEQUENCE OF LocatedQuantity

ObjectAttributeToxicCloud ::= SEQUENCE
{
    quantities    LocatedQuantityList
}

ObjectAttributeMine ::= SEQUENCE
{
    dotation-type   DotationType        OPTIONAL,        
    dotation-nbr    INTEGER             OPTIONAL,
    density         REAL                OPTIONAL,
    percentage      INTEGER( 0..100 )   OPTIONAL
}

ObjectAttributeActivityTime ::= SEQUENCE
{
    value   INTEGER -- en heure
}

ObjectAttributeNBC ::= SEQUENCE
{
    danger-level        INTEGER(0..10),
    nbc-agents  ListOID -- Cf. Data/NBC.xml
}

ObjectAttributeObstacle ::= SEQUENCE
{
    type        EnumDemolitionTargetType,
    activated   BOOLEAN
}

ObjectAttributeCrossingSite ::= SEQUENCE
{
    width                 INTEGER,    -- en mètres
    depth                 INTEGER,    -- en mètres
    flow-rate             INTEGER,    -- en m/s
    banks-require-fitting BOOLEAN
}

ObjectAttributeSupplyRoute ::= SEQUENCE
{
    equipped    BOOLEAN,
    max-weight  INTEGER,
    width       INTEGER,
    length      INTEGER,
    flow-rate   INTEGER
}

ObjectAttributeFire ::= SEQUENCE
{
    class-id	OID, -- Cf. Data/Fire.xml
    heat		INTEGER
}

ObjectAttributeNBCType ::= SEQUENCE
{
    agent-id				OID, -- Cf. Data/NBCType.xml
    concentration			INTEGER,
    source-life-duration	INTEGER
}

ObjectAttributeMedicalTreatment ::= SEQUENCE
{
	type-id			  ListOID, -- Cf. Data/MedicalTreatment.xml
	beds			  INTEGER,
	available-beds	  INTEGER,
	doctors			  INTEGER,
	available-doctors INTEGER
}

StockResource ::= SEQUENCE
{    
    dotation-type   DotationType,
    current         INTEGER,
    max             INTEGER OPTIONAL
}
StockResourceList ::= SEQUENCE OF StockResource
ObjectAttributeStock ::= SEQUENCE
{
    resources       StockResourceList
}

ObjectAttributes ::= SEQUENCE
{
    construction		ObjectAttributeConstruction OPTIONAL,
    obstacle			ObjectAttributeObstacle OPTIONAL,
    mine				ObjectAttributeMine OPTIONAL,    
    activity-time		ObjectAttributeActivityTime OPTIONAL,    
    bypass				ObjectAttributeBypass OPTIONAL,
    logistic			ObjectAttributeLogistic OPTIONAL,
    nbc					ObjectAttributeNBC OPTIONAL,
    crossing-site		ObjectAttributeCrossingSite OPTIONAL,
    supply-route		ObjectAttributeSupplyRoute OPTIONAL,
    toxic-cloud			ObjectAttributeToxicCloud OPTIONAL,
    fire				ObjectAttributeFire OPTIONAL,
    medical-treatment	ObjectAttributeMedicalTreatment OPTIONAL,
    interaction-height	ObjectAttributeInteractionHeight OPTIONAL,
    nbc-agent			ObjectAttributeNBCType OPTIONAL,
    stock			    ObjectAttributeStock OPTIONAL
}

-- ObjectAttributes ::= SEQUENCE OF ObjectAttribute
 
---------------------------
-- Objet réel
---------------------------     

MsgObjectCreation ::= SEQUENCE
{
    oid         OID,
    type        VisibleString,
    name        VisibleString,
    team        Team,
    location    Location,
    attributes  ObjectAttributes
}

MsgObjectUpdate ::= SEQUENCE
{
    oid             OID,
    location        Location OPTIONAL,
    attributes      ObjectAttributes
}

MsgObjectDestruction ::= OID


---------------------------
-- Actions magiques
---------------------------

MagicActionUpdateObject ::= SEQUENCE
{
    oid                             OID,    
    attributes                      ObjectAttributes
}

MagicActionCreateObject ::= SEQUENCE
{        
    type        VisibleString,    
    location    Location,
    name        VisibleString,
    team        Team,
    attributes  ObjectAttributes
}

MagicActionDestroyObjet ::= OID -- oid-objet

MsgObjectMagicAction ::= SEQUENCE
{
    action CHOICE
    {
        create-object   MagicActionCreateObject,
        update-object   MagicActionUpdateObject,
        destroy-object  MagicActionDestroyObjet
    }       
}

MsgObjectMagicActionAck ::= SEQUENCE
{
    error-code  EnumObjectErrorCode
}

END -- Object
