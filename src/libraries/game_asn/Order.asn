--
-- file name : Order.asn
--
-- Fichier contenant les types et messages communs à tous les types d'ordres
--

Order DEFINITIONS AUTOMATIC TAGS ::= BEGIN

-- BEGIN includes
IMPORTS BaseExports           FROM Base
        LimaLimiteExports     FROM LimaLimite
        LogMaintenanceExports FROM LogMaintenance
        LogSanteExports       FROM LogSante
        ObjectExports         FROM Object
        IntelligenceExports   FROM Intelligence;
OrderIncludes ::= SEQUENCE { BaseExports, LimaLimiteExports, LogMaintenanceExports, LogSanteExports, ObjectExports, IntelligenceExports }
OrderExports  ::= NULL
-- END includes

EnumOrderErrorCode ::= ENUMERATED
{
    no-error                                (0),
    error-invalid-unit                      (1),
    error-invalid-limit                     (2),
    error-invalid-lima                      (3),
    error-invalid-mission                   (4),
    error-invalid-mission-parameters        (5),
    error-unit-cannot-receive-order         (6),
    error-invalid-order-conduite            (7),
    error-invalid-order-mission             (8),
    error-invalid-order-initial             (9),
    error-invalid-order-conduite-parameters (10),
    error-unit-surrendered                  (11),
    error-invalid-lima-function             (12)
}

-- TEST MISSIONS GENERIQUES

MissionObjective ::= SEQUENCE
{
    localisation Location,
    horaire      DateTime
}
MissionObjectiveList ::= SEQUENCE OF MissionObjective

PlannedWork ::= SEQUENCE
{
    type                 VisibleString,
    position             Location,
    type-obstacle        EnumDemolitionTargetType DEFAULT preliminary,
    densite              REAL(0..5)       DEFAULT 0,
    tc2                  Automat          DEFAULT 0,
    activity-time        INTEGER          DEFAULT 0
}
PlannedWorkList ::= SEQUENCE OF PlannedWork

MissionParameter ::= SEQUENCE
{
    null-value BOOLEAN DEFAULT FALSE,
    value      CHOICE
    {
        BOOLEAN,
        REAL,
        enumeration INTEGER,
        Path,
        PathList,
        Point,
        PointList,
        Polygon,
        PolygonList,
        Location,
        LocationList,
        Heading,
        AtlasNature,
        Unit,
        UnitList,
        Automat,
        AutomatList,
        UnitKnowledge,
        UnitKnowledgeList,
        ObjectKnowledge,
        ObjectKnowledgeList,
        PopulationKnowledge,
        PlannedWork,
        PlannedWorkList,
        DotationType,
        EquipmentType,
        tirIndirect UnitFire,
        DateTime,
        LogMaintenancePriorities,
        LogMedicalPriorities,
        VisibleString,
        MissionObjective,
        MissionObjectiveList,
        Line,
        LimasOrder,
        IntelligenceList,
        UrbanBlock
    }
}

MissionParameters ::= SEQUENCE OF MissionParameter

--
-- Pion
--
MsgUnitOrder ::= SEQUENCE
{
    oid             Unit,
    mission         OID,
    parametres      MissionParameters
}
MsgUnitOrderAck ::= SEQUENCE
{
    oid         Unit,
    error-code  EnumOrderErrorCode
}

--
-- Automat
--
EnumAutomatOrderFormation ::= ENUMERATED
{
    un-echelon      (0),
    deux-echelons   (1)
}
MsgAutomatOrder ::= SEQUENCE
{
    oid           Automat,
    mission       OID,
    parametres    MissionParameters
}

MsgAutomatOrderAck ::= SEQUENCE
{
    oid         Automat,
    error-code  EnumOrderErrorCode
}

--
-- Population
--
MsgPopulationOrder ::= SEQUENCE
{
    oid         Population,
    mission     OID,
    parametres  MissionParameters
}
MsgPopulationOrderAck ::= SEQUENCE
{
    oid         Population,
    error-code  EnumOrderErrorCode
}

--
-- Frag orders
--
MsgFragOrder ::= SEQUENCE
{
    oid         OID,
    frag-order  OID,
    parametres  MissionParameters
}
MsgFragOrderAck ::= SEQUENCE
{
    oid         OID,
    error-code  EnumOrderErrorCode
}

-- CR

EnumReportType ::= ENUMERATED
{
    message                 (0),
    operationel             (1),
    evenement-exceptionnel  (2),
    warning                 (3)
}

MsgReport ::= SEQUENCE
{
    oid        OID, -- Automat, pion ou population
    cr         OID,
    cr-oid     OID,
    type       EnumReportType,
    time       DateTime,
    parametres MissionParameters
}

MsgInvalidateReport ::= SEQUENCE
{
    oid     OID, -- Automat, pion ou population
    cr-oid  OID
}

MsgTrace ::= SEQUENCE
{
    oid     OID, -- Automat, pion ou population
    message VisibleString
}

MsgDecisionalState ::= SEQUENCE
{
    oid    OID, -- Automat, pion ou population
    key    VisibleString,
    value  VisibleString
}

MsgDebugPoints ::= SEQUENCE
{
    oid         OID, -- Automat, pion ou population
    coordinates CoordLatLongList
}

END -- Order
