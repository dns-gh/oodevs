--
-- file name : LogMaintenance.asn
--
-- Messages de gestion de la chaine logistique maintenance
--

LogMaintenance DEFINITIONS AUTOMATIC TAGS ::= BEGIN

-- BEGIN includes
IMPORTS BaseExports FROM Base;
LogMaintenanceIncludes ::= SEQUENCE { BaseExports }
LogMaintenanceExports  ::= NULL
-- END includes

EnumLogMaintenanceRegimeTravail ::= ENUMERATED
{
    regime-1,
    regime-2,
    regime-3,
    regime-4    
}

MsgLogMaintenanceHandlingCreation ::= SEQUENCE
{
    oid-consigne    OID,
    oid-pion        Unit,          -- pion possèdant l'equipement
    tick-creation   INTEGER,
    type-equipement EquipmentType,
    type-panne      BreakdownType       -- Cf. data/pannes.xml
}

EnumLogMaintenanceHandlingStatus ::= ENUMERATED
{ 
    deplacement-vers-chaine                     (0),         
    attente-disponibilite-remorqueur            (1),
    remorqueur-deplacement-aller                (2),
    remorqueur-chargement                       (3),
    remorqueur-deplacement-retour               (4),
    remorqueur-dechargement                     (5),
    diagnostique                                (6),
    attente-prise-en-charge-par-niveau-superieur(7),
    attente-disponibilite-pieces                (8),
    attente-disponibilite-reparateur            (9),
    reparation                                  (10),
    retour-pion                                 (11),
    termine                                     (12)
}

MsgLogMaintenanceHandlingUpdate ::= SEQUENCE
{
    oid-consigne          OID,
    oid-pion              Unit,                            -- pion possèdant l'equipement
    oid-pion-log-traitant Unit,                            -- pion LOG gérant la maintenance de l'equipement, 0 si aucun pion (demande passée à la BLIAT par exemple)
    etat                  EnumLogMaintenanceHandlingStatus OPTIONAL,
    diagnostique-effectue BOOLEAN                          OPTIONAL
}


MsgLogMaintenanceHandlingDestruction ::= SEQUENCE
{
    oid-consigne    OID,
    oid-pion        Unit          -- pion possèdant l'equipement    
}

-- Etat des pions logistiques de la maintenance
LogMaintenanceEquipmentAvailability ::= SEQUENCE
{
    type-equipement  EquipmentType,
    nbr-total        INTEGER,
    nbr-disponibles  INTEGER,       
    nbr-au-travail   INTEGER,
    nbr-pretes       INTEGER DEFAULT 0,
    nbr-au-repos     INTEGER OPTIONAL -- applicable uniquement à certains moyens
}

LogMaintenancePriorities ::= SEQUENCE OF EquipmentType

MsgLogMaintenanceState ::= SEQUENCE
{
    oid-pion                   Unit,
    chaine-activee             BOOLEAN                                    OPTIONAL,
    regime-travail             EnumLogMaintenanceRegimeTravail            OPTIONAL,
    priorites                  LogMaintenancePriorities                       OPTIONAL, 
    priorites-tactiques        AutomatList                               OPTIONAL,
    disponibilites-remorqueurs SEQUENCE OF LogMaintenanceEquipmentAvailability OPTIONAL,
    disponibilites-reparateurs SEQUENCE OF LogMaintenanceEquipmentAvailability OPTIONAL
}

END -- LogMaintenance
