--
-- file name : XmliaTextMessage.asn
--
-- Messages texte xmlia sim vers client
--

InfoMessage DEFINITIONS AUTOMATIC TAGS ::= BEGIN

-- BEGIN includes
IMPORTS BaseExports FROM Base;
InfoMessageIncludes ::= SEQUENCE { BaseExports }
InfoMessageExports  ::= NULL
-- END includes

MsgXmliaTextMessage ::= SEQUENCE
{
    destinataire                     VisibleString ,    
    message                     VisibleString          
}

END -- InfoMessage
