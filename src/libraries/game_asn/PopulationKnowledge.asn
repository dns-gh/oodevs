--
-- file name : PopulationKnowledge.asn
--
-- Messages de gestion des objets
--

PopulationKnowledge DEFINITIONS AUTOMATIC TAGS ::= BEGIN

-- BEGIN includes
IMPORTS BaseExports       FROM Base
        PopulationExports FROM Population;
PopulationKnowledgeIncludes ::= SEQUENCE { BaseExports, PopulationExports }
PopulationKnowledgeExports  ::= NULL
-- END includes

-------------------
-- Population
-------------------

MsgPopulationKnowledgeCreation ::= SEQUENCE
{  
    oid-connaissance      OID,
    oid-groupe-possesseur OID, -- Groupe de connaissance possedant la connaissance
    
    oid-population-reelle OID,
    camp                  OID  -- Team de la population    
}

MsgPopulationKnowledgeUpdate ::= SEQUENCE
{
    oid-connaissance      OID,
    oid-groupe-possesseur OID, -- Groupe de connaissance possedant la connaissance
    etat-domination       Percentage OPTIONAL
}

MsgPopulationKnowledgeDestruction ::= SEQUENCE
{
    oid-connaissance      OID,
    oid-groupe-possesseur OID -- Groupe de connaissance possedant la connaissance
}

-------------------
-- Concentration
-------------------

MsgPopulationConcentrationKnowledgeCreation ::= SEQUENCE
{
    oid-connaissance-concentration  OID,
    oid-connaissance-population     OID,
    oid-groupe-possesseur           OID, -- Groupe de connaissance possedant la connaissance
    
    oid-concentration-reelle        OID,
    position                        CoordLatLong
}

MsgPopulationConcentrationKnowledgeUpdate ::= SEQUENCE
{
    oid-connaissance-concentration  OID,
    oid-connaissance-population     OID,
    oid-groupe-possesseur           OID, -- Groupe de connaissance possedant la connaissance
    
    oid-concentration-reelle        OID                    OPTIONAL, 
    nb-humains-vivants              INTEGER                OPTIONAL,
    nb-humains-morts                INTEGER                OPTIONAL,
    attitude                        EnumPopulationAttitude OPTIONAL,
    pertinence                      Percentage            OPTIONAL,
    est-percu                       BOOLEAN                OPTIONAL
}

MsgPopulationConcentrationKnowledgeDestruction ::= SEQUENCE
{
    oid-connaissance-concentration  OID,
    oid-connaissance-population     OID,
    oid-groupe-possesseur           OID -- Groupe de connaissance possedant la connaissance
}


-------------------
-- Flux
-------------------

MsgPopulationFlowKnowledgeCreation ::= SEQUENCE
{
    oid-connaissance-flux       OID,
    oid-connaissance-population OID,
    oid-groupe-possesseur       OID, -- Groupe de connaissance possedant la connaissance
    oid-flux-reel               OID
}

FlowPart ::= SEQUENCE
{
    forme       Path,
    pertinence  Percentage       
}

MsgPopulationFlowKnowledgeUpdate ::= SEQUENCE
{
    oid-connaissance-flux       OID,
    oid-connaissance-population OID,
    oid-groupe-possesseur       OID, -- Groupe de connaissance possedant la connaissance
    
    oid-flux-reel               OID                     OPTIONAL, 
    portions-flux               SEQUENCE OF FlowPart OPTIONAL,
    direction                   Heading               OPTIONAL, -- en degres
    vitesse                     Speed                 OPTIONAL, -- en km/h
    nb-humains-vivants          INTEGER                 OPTIONAL,
    nb-humains-morts            INTEGER                 OPTIONAL,
    attitude                    EnumPopulationAttitude  OPTIONAL,
    est-percu                   BOOLEAN                 OPTIONAL    
}

MsgPopulationFlowKnowledgeDestruction ::= SEQUENCE
{
    oid-connaissance-flux       OID,
    oid-connaissance-population OID,
    oid-groupe-possesseur       OID -- Groupe de connaissance possedant la connaissance
}


END -- PopulationKnowledge
