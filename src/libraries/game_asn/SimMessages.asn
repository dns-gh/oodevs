--
-- file name : SimMessages.asn
--
-- Liste des messages
--

SimMessages DEFINITIONS AUTOMATIC TAGS ::= BEGIN

-- BEGIN includes
IMPORTS BaseExports                   FROM Base
        OrderExports                  FROM Order
        ControlExports                FROM Control
        KnowledgeGroupExports         FROM KnowledgeGroup
        FormationExports              FROM Formation
        FireExports                   FROM Fire
        UnitExports                   FROM Unit
        UnitKnowledgeExports          FROM UnitKnowledge
        ObjectExports                 FROM Object
        ObjectKnowledgeExports        FROM ObjectKnowledge
        PopulationExports             FROM Population
        PopulationKnowledgeExports    FROM PopulationKnowledge
        LogMaintenanceExports         FROM LogMaintenance
        LogRavitaillementExports      FROM LogRavitaillement
        LogSanteExports               FROM LogSante
        AutomateExports               FROM Automat
        ArmyExports                   FROM Army
        AuthExports                   FROM Auth
        FolkExports                   FROM Folk
        UrbanExports                  FROM Urban
        UrbanKnowledgeExports         FROM UrbanKnowledge;

SimMessagesIncludes ::= SEQUENCE
{ BaseExports, OrderExports, ControlExports, KnowledgeGroupExports,
  FormationExports, FireExports, UnitExports, UnitKnowledgeExports, ObjectExports,
  ObjectKnowledgeExports, PopulationExports, PopulationKnowledgeExports, LogMaintenanceExports,
  LogRavitaillementExports, LogSanteExports, AutomateExports, ArmyExports, AuthExports, FolkExports, UrbanExports, UrbanKnowledgeExports}
SimMessagesExports  ::= NULL
-- END includes


--
--
--
MsgsSimToClient ::= SEQUENCE
{
    context INTEGER DEFAULT 0,
    msg     CHOICE
    {
        -- ACKS
        msg-unit-order-ack                                      MsgUnitOrderAck,
        msg-automat-order-ack                                   MsgAutomatOrderAck,
        msg-population-order-ack                                MsgPopulationOrderAck,
        msg-frag-order-ack                                      MsgFragOrderAck,
        msg-set-automat-mode-ack                                MsgSetAutomatModeAck,
        msg-unit-creation-request-ack                           MsgUnitCreationRequestAck,
        msg-unit-magic-action-ack                               MsgUnitMagicActionAck,
        msg-object-magic-action-ack                             MsgObjectMagicActionAck,
        msg-population-magic-action-ack                         MsgPopulationMagicActionAck,

        msg-change-diplomacy-ack                                MsgChangeDiplomacyAck,
        msg-automat-change-knowledge-group-ack                  MsgAutomatChangeKnowledgeGroupAck,
        msg-automat-change-logistic-links-ack                   MsgAutomatChangeLogisticLinksAck,
        msg-automat-change-superior-ack                         MsgAutomatChangeSuperiorAck,
        msg-unit-change-superior-ack                            MsgUnitChangeSuperiorAck,   
        
        msg-log-supply-push-flow-ack                            MsgLogSupplyPushFlowAck,
        msg-log-supply-change-quotas-ack                        MsgLogSupplyChangeQuotasAck,
        -- LTO begin
        msg-knowledge-group-change-superior-ack                 MsgKnowledgeGroupChangeSuperiorAck,
        msg-knowledge-group-delete-ack                          MsgKnowledgeGroupDeleteAck,
        msg-knowledge-group-set-type-ack                        MsgKnowledgeGroupSetTypeAck,
        msg-knowledge-group-creation-ack                        MsgKnowledgeGroupCreationAck,
        -- LTO end

        -- MESSAGES
        msg-control-information                                 MsgControlInformation,
        msg-control-profiling-information                       MsgControlProfilingInformation,
        msg-control-begin-tick                                  MsgControlBeginTick,
        msg-control-end-tick                                    MsgControlEndTick,
        msg-control-stop-ack                                    MsgControlStopAck,
        msg-control-pause-ack                                   MsgControlPauseAck,
        msg-control-resume-ack                                  MsgControlResumeAck,
        msg-control-change-time-factor-ack                      MsgControlChangeTimeFactorAck,
        msg-control-date-time-change-ack                        MsgControlDatetimeChangeAck,
        msg-control-global-meteo-ack                            MsgControlGlobalMeteoAck,
        msg-control-local-meteo-ack                             MsgControlLocalMeteoAck,
        msg-control-checkpoint-save-begin                       MsgControlCheckPointSaveBegin,
        msg-control-checkpoint-save-end                         MsgControlCheckPointSaveEnd,
        msg-control-checkpoint-set-frequency-ack                MsgControlCheckPointSetFrequencyAck,
        msg-control-checkpoint-save-now-ack                     MsgControlCheckPointSaveNowAck,
        msg-control-send-current-state-begin                    MsgControlSendCurrentStateBegin,
        msg-control-send-current-state-end                      MsgControlSendCurrentStateEnd,

        msg-formation-creation                                  MsgFormationCreation,
        msg-knowledge-group-creation                            MsgKnowledgeGroupCreation,
        msg-side-creation                                       MsgTeamCreation,

        msg-automat-creation                                    MsgAutomatCreation,
        msg-automat-attributes                                  MsgAutomatAttributes,

        msg-unit-creation                                       MsgUnitCreation,
        msg-unit-attributes                                     MsgUnitAttributes,
        msg-unit-pathfind                                       MsgUnitPathFind,
        msg-unit-destruction                                    MsgUnitDestruction,
        msg-unit-environment-type                               MsgUnitEnvironmentType,

        msg-change-diplomacy                                    MsgChangeDiplomacy,
        msg-unit-change-superior                                MsgUnitChangeSuperior,
        msg-automat-change-logistic-links                       MsgAutomatChangeLogisticLinks,
        msg-automat-change-knowledge-group                      MsgAutomatChangeKnowledgeGroup,
        msg-automat-change-superior                             MsgAutomatChangeSuperior,

        msg-unit-knowledge-creation                             MsgUnitKnowledgeCreation,
        msg-unit-knowledge-update                               MsgUnitKnowledgeUpdate,
        msg-unit-knowledge-destruction                          MsgUnitKnowledgeDestruction,

        msg-start-unit-fire                                     MsgStartUnitFire,
        msg-stop-unit-fire                                      MsgStopUnitFire,
        msg-start-population-fire                               MsgStartPopulationFire,
        msg-stop-population-fire                                MsgStopPopulationFire,
        msg-explosion                                           MsgExplosion,
        msg-start-fire-effect                                   MsgStartFireEffect,
        msg-stop-fire-effect                                    MsgStopFireEffect,

        msg-report                                              MsgReport,
        msg-invalidate-report                                   MsgInvalidateReport,
        msg-trace                                               MsgTrace,
        msg-decisional-state                                    MsgDecisionalState,
        msg-debug-points                                        MsgDebugPoints,

        msg-unit-vision-cones                                   MsgUnitVisionCones,
        msg-unit-detection                                      MsgUnitDetection,
        msg-object-detection                                    MsgObjectDetection,
        msg-urban-detection                                     MsgUrbanDetection,
        msg-population-concentration-detection                  MsgPopulationConcentrationDetection,
        msg-population-flow-detection                           MsgPopulationFlowDetection,

        msg-unit-order                                          MsgUnitOrder,
        msg-automat-order                                       MsgAutomatOrder,
        msg-population-order                                    MsgPopulationOrder,

        msg-object-creation                                     MsgObjectCreation,
        msg-object-destruction                                  MsgObjectDestruction,
        msg-object-update                                       MsgObjectUpdate,
        msg-object-knowledge-creation                           MsgObjectKnowledgeCreation,
        msg-object-knowledge-update                             MsgObjectKnowledgeUpdate,
        msg-object-knowledge-destruction                        MsgObjectKnowledgeDestruction,

        msg-log-medical-handling-creation                       MsgLogMedicalHandlingCreation,
        msg-log-medical-handling-update                         MsgLogMedicalHandlingUpdate,
        msg-log-medical-handling-destruction                    MsgLogMedicalHandlingDestruction,
        msg-log-medical-state                                   MsgLogMedicalState,

        msg-log-maintenance-handling-creation                   MsgLogMaintenanceHandlingCreation,
        msg-log-maintenance-handling-update                     MsgLogMaintenanceHandlingUpdate,
        msg-log-maintenance-handling-destruction                MsgLogMaintenanceHandlingDestruction,
        msg-log-maintenance-state                               MsgLogMaintenanceState,

        msg-log-supply-handling-creation                        MsgLogSupplyHandlingCreation,
        msg-log-supply-handling-update                          MsgLogSupplyHandlingUpdate,
        msg-log-supply-handling-destruction                     MsgLogSupplyHandlingDestruction,
        msg-log-supply-state                                    MsgLogSupplyState,
        msg-log-supply-quotas                                   MsgLogSupplyQuotas,

        msg-population-creation                                 MsgPopulationCreation,
        msg-population-update                                   MsgPopulationUpdate,
        msg-population-concentration-creation                   MsgPopulationConcentrationCreation,
        msg-population-concentration-destruction                MsgPopulationConcentrationDestruction,
        msg-population-concentration-update                     MsgPopulationConcentrationUpdate,
        msg-population-flow-creation                            MsgPopulationFlowCreation,
        msg-population-flow-destruction                         MsgPopulationFlowDestruction,
        msg-population-flow-update                              MsgPopulationFlowUpdate,

        msg-population-knowledge-creation                       MsgPopulationKnowledgeCreation,
        msg-population-knowledge-update                         MsgPopulationKnowledgeUpdate,
        msg-population-knowledge-destruction                    MsgPopulationKnowledgeDestruction,
        msg-population-concentration-knowledge-creation         MsgPopulationConcentrationKnowledgeCreation,
        msg-population-concentration-knowledge-destruction      MsgPopulationConcentrationKnowledgeDestruction,
        msg-population-concentration-knowledge-update           MsgPopulationConcentrationKnowledgeUpdate,
        msg-population-flow-knowledge-creation                  MsgPopulationFlowKnowledgeCreation,
        msg-population-flow-knowledge-destruction               MsgPopulationFlowKnowledgeDestruction,
        msg-population-flow-knowledge-update                    MsgPopulationFlowKnowledgeUpdate,

        msg-folk-creation                                       MsgFolkCreation,
        msg-folk-graph-update                                   MsgFolkGraphUpdate,
        
        msg-urban-creation                                      MsgUrbanCreation,
        msg-urban-knowledge-creation                            MsgUrbanKnowledgeCreation,
        msg-urban-knowledge-update                              MsgUrbanKnowledgeUpdate,
        msg-urban-knowledge-destruction                         MsgUrbanKnowledgeDestruction,
        
        msg-knowledge-group-update                              MsgKnowledgeGroupUpdate, -- LTO
        msg-knowledge-group-delete                              MsgKnowledgeGroupDelete -- LTO
    }
}

MsgsClientToSim ::= SEQUENCE
{
    context INTEGER DEFAULT 0,
    msg     CHOICE
    {
        msg-control-stop                        MsgControlStop,
        msg-control-pause                       MsgControlPause,
        msg-control-resume                      MsgControlResume,
        msg-control-change-time-factor          MsgControlChangeTimeFactor,
        msg-control-date-time-change            MsgControlDatetimeChange,
        msg-control-global-meteo                MsgControlGlobalMeteo,
        msg-control-local-meteo                 MsgControlLocalMeteo,
        msg-control-checkpoint-save-now         MsgControlCheckPointSaveNow,
        msg-control-checkpoint-set-frequency    MsgControlCheckPointSetFrequency,
        msg-control-toggle-vision-cones         MsgControlToggleVisionCones,

        msg-unit-order                          MsgUnitOrder,
        msg-automat-order                       MsgAutomatOrder,
        msg-population-order                    MsgPopulationOrder,
        msg-frag-order                          MsgFragOrder,

        msg-set-automat-mode                    MsgSetAutomatMode,
        msg-unit-creation-request               MsgUnitCreationRequest,

        msg-unit-magic-action                   MsgUnitMagicAction,
        msg-object-magic-action                 MsgObjectMagicAction,
        msg-population-magic-action             MsgPopulationMagicAction,

        msg-change-diplomacy                    MsgChangeDiplomacy,
        msg-automat-change-knowledge-group      MsgAutomatChangeKnowledgeGroup,
        msg-automat-change-logistic-links       MsgAutomatChangeLogisticLinks,
        msg-automat-change-superior             MsgAutomatChangeSuperior,
        msg-unit-change-superior                MsgUnitChangeSuperior,

        msg-log-supply-push-flow                MsgLogSupplyPushFlow,
        msg-log-supply-change-quotas            MsgLogSupplyChangeQuotas,
        -- LTO begin
        msg-knowledge-group-change-superior     MsgKnowledgeGroupChangeSuperior,
        msg-knowledge-group-creation            MsgKnowledgeGroupCreation,
        msg-knowledge-group-delete              MsgKnowledgeGroupDelete,
        msg-knowledge-group-set_type            MsgKnowledgeGroupSetType,
        msg-knowledge-group-enable              MsgKnowledgeGroupEnable
        -- LTO end
    }
}

END
