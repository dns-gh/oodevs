--
-- file name : ScipioAuth.asn
--
-- Messages de gestion des profils
--

ScipioAuth DEFINITIONS AUTOMATIC TAGS ::= BEGIN

-- BEGIN includes
IMPORTS ScipioBaseExports FROM ScipioBase;
ScipioAuthIncludes ::= SEQUENCE { ScipioBaseExports }
ScipioAuthExports  ::= NULL
-- END includes

--------------------
-- AUTH / PROFILES
--------------------

Profile ::= SEQUENCE
{
    login                   VisibleString,
    password                VisibleString  OPTIONAL,
    read-only-formations    ListFormation  OPTIONAL,
    read-write-formations   ListFormation  OPTIONAL,
    read-only-automates     ListAutomate   OPTIONAL,
    read-write-automates    ListAutomate   OPTIONAL,
    read-only-camps         ListCamp       OPTIONAL,
    read-write-camps        ListCamp       OPTIONAL,
    read-only-populations   ListPopulation OPTIONAL,
    read-write-populations  ListPopulation OPTIONAL,
    superviseur             BOOLEAN
}

MsgAuthenticationRequest ::= SEQUENCE
{
    login    VisibleString,
    password VisibleString 
}

MsgAuthenticationResponse ::= SEQUENCE
{
    error-code ENUMERATED
    {   
        success,
        invalid-login
    },
    profile Profile OPTIONAL -- only if success
}

MsgProfileCreation           ::= Profile
MsgProfileCreationRequest    ::= Profile
MsgProfileCreationRequestAck ::= SEQUENCE
{
    error-code ENUMERATED
    {
        success,
        invalid-login,
        invalid-password,
        duplicate-login
    },
    login VisibleString -- login of profile to be created
}

MsgProfileUpdate           ::= SEQUENCE
{
    login   VisibleString, -- login of profile to update
    profile Profile        -- updated profile
}

MsgProfileUpdateRequest    ::= SEQUENCE
{
    login   VisibleString, -- login of profile to update
    profile Profile        -- updated profile
}

MsgProfileUpdateRequestAck ::= SEQUENCE
{
    error-code ENUMERATED
    {
        success,
        invalid-profile,
        invalid-login,
        invalid-password,
        duplicate-login
    },
    login VisibleString    -- login of profile to be updated
}

MsgProfileDestruction           ::= VisibleString
MsgProfileDestructionRequest    ::= VisibleString
MsgProfileDestructionRequestAck ::= SEQUENCE
{
    error-code ENUMERATED
    {
        success,
        invalid-profile,
        failure
    },
    login VisibleString    -- login of profile to be deleted
}

END -- ScipioAuth
