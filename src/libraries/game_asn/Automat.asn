--
-- file name : AutomatetAttr.asn
--
-- Messages de gestion des attributs d'une unité
--

Automat DEFINITIONS AUTOMATIC TAGS ::= BEGIN

-- BEGIN includes
IMPORTS BaseExports FROM Base
        UnitExports FROM Unit;
AutomateIncludes ::= SEQUENCE { BaseExports, UnitExports }
AutomateExports  ::= NULL
-- END includes

EnumAutomatMode ::= ENUMERATED
{
    embraye,
    debraye
}

MsgAutomatCreation ::= SEQUENCE
{
    oid                      Automat,
    type-automate            AutomatType,
    nom                      VisibleString,
    oid-parent               CHOICE
    {
        formation Formation,
        automate  Automat
    },
    oid-camp                 Team,
    oid-groupe-connaissance  OID
}

MsgAutomatAttributes ::= SEQUENCE
{
    oid                           Automat,
    etat-automate                 EnumAutomatMode               OPTIONAL,
    rapport-de-force              EnumForceRatioStatus          OPTIONAL,
    combat-de-rencontre           EnumMeetingEngagementStatus   OPTIONAL,
    etat-operationnel             EnumOperationalStatus         OPTIONAL,
    roe                           EnumRoe                       OPTIONAL
}

-- Misc
EnumSetAutomatModeErrorCode ::= ENUMERATED
{
    no-error          (0),
    error-invalid-unit(1),
    error-not-allowed (2)
}
MsgSetAutomatMode ::= SEQUENCE
{
    oid     Automat,
    mode    EnumAutomatMode
}
MsgSetAutomatModeAck ::= SEQUENCE
{
    oid         Automat,
    error-code  EnumSetAutomatModeErrorCode
}

-- Changement hierarchie
MsgAutomatChangeKnowledgeGroup ::= SEQUENCE
{
    oid                      Automat,
    oid-camp                 Team,
    oid-groupe-connaissance  KnowledgeGroup
}

MsgAutomatChangeSuperior ::= SEQUENCE
{
    oid           Automat,
    oid-superior  CHOICE
    {
        formation Formation,
        automate  Automat
    }
}

MsgAutomatChangeLogisticLinks ::= SEQUENCE
{
    oid                Automat,
    oid-tc2            Automat OPTIONAL,
    oid-maintenance    Automat OPTIONAL,
    oid-sante          Automat OPTIONAL,
    oid-ravitaillement Automat OPTIONAL
}

MsgAutomatChangeSuperiorAck       ::= EnumChangeHierarchyErrorCode
MsgAutomatChangeKnowledgeGroupAck ::= EnumChangeHierarchyErrorCode
MsgAutomatChangeLogisticLinksAck  ::= EnumChangeHierarchyErrorCode

END -- Automat
