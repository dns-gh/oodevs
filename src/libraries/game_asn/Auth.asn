--
-- file name : Auth.asn
--
-- Messages de gestion des profils
--

Auth DEFINITIONS AUTOMATIC TAGS ::= BEGIN

-- BEGIN includes
IMPORTS BaseExports FROM Base;
AuthIncludes ::= SEQUENCE { BaseExports }
AuthExports  ::= NULL
-- END includes

--------------------
-- AUTH / PROFILES
--------------------

Profile ::= SEQUENCE
{
    login                   VisibleString,
    password                VisibleString  OPTIONAL,
    read-only-formations    FormationList  OPTIONAL,
    read-write-formations   FormationList  OPTIONAL,
    read-only-automates     AutomatList   OPTIONAL,
    read-write-automates    AutomatList   OPTIONAL,
    read-only-camps         TeamList       OPTIONAL,
    read-write-camps        TeamList       OPTIONAL,
    read-only-populations   PopulationList OPTIONAL,
    read-write-populations  PopulationList OPTIONAL,
    superviseur             BOOLEAN
}

MsgAuthenticationRequest ::= SEQUENCE
{
    login    VisibleString,
    password VisibleString 
}

MsgAuthenticationResponse ::= SEQUENCE
{
    error-code ENUMERATED
    {   
        success,
        invalid-login
    },
    profile Profile OPTIONAL -- only if success
}

MsgProfileCreation           ::= Profile
MsgProfileCreationRequest    ::= Profile
MsgProfileCreationRequestAck ::= SEQUENCE
{
    error-code ENUMERATED
    {
        success,
        invalid-login,
        invalid-password,
        duplicate-login
    },
    login VisibleString -- login of profile to be created
}

MsgProfileUpdate           ::= SEQUENCE
{
    login   VisibleString, -- login of profile to update
    profile Profile        -- updated profile
}

MsgProfileUpdateRequest    ::= SEQUENCE
{
    login   VisibleString, -- login of profile to update
    profile Profile        -- updated profile
}

MsgProfileUpdateRequestAck ::= SEQUENCE
{
    error-code ENUMERATED
    {
        success,
        invalid-profile,
        invalid-login,
        invalid-password,
        duplicate-login
    },
    login VisibleString    -- login of profile to be updated
}

MsgProfileDestruction           ::= VisibleString
MsgProfileDestructionRequest    ::= VisibleString
MsgProfileDestructionRequestAck ::= SEQUENCE
{
    error-code ENUMERATED
    {
        success,
        invalid-profile,
        failure
    },
    login VisibleString    -- login of profile to be deleted
}

END -- Auth
