--
-- file name : AutomatetAttr.asn
--
-- Messages de gestion des attributs d'une unité
--

Army DEFINITIONS AUTOMATIC TAGS ::= BEGIN

-- BEGIN includes
IMPORTS BaseExports FROM Base;
ArmyIncludes ::= SEQUENCE { BaseExports }
ArmyExports  ::= NULL
-- END includes

EnumDiplomacy ::= ENUMERATED
{
    inconnu (0),
    ami     (1),
    ennemi  (2),
    neutre  (3)
}

MsgChangeDiplomacy ::= SEQUENCE
{
    oid-camp1  Team,
    oid-camp2  Team,
    diplomatie EnumDiplomacy 
}

EnumChangeDiplomacyErrorCode ::= ENUMERATED
{
    no-error            (0),
    error-invalid-camp  (1)
}

MsgTeamCreation ::= SEQUENCE
{
    oid  Team,
    nom  VisibleString,
    type EnumDiplomacy
}

MsgChangeDiplomacyAck ::= SEQUENCE
{
    oid-camp1  Team,
    oid-camp2  Team,
    diplomatie EnumDiplomacy,
    error-code EnumChangeDiplomacyErrorCode
}

END -- Army
