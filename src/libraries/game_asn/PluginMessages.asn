--
-- file name : PluginMessages.asn
--
-- plug-in messages list
--

PluginMessages DEFINITIONS AUTOMATIC TAGS ::= BEGIN

-- BEGIN includes
IMPORTS PluginExports FROM Plugin
        LimaLimiteExports             FROM LimaLimite
        IntelligenceExports           FROM Intelligence;

PluginMessagesIncludes ::= SEQUENCE
{ PluginExports }
PluginMessagesExports  ::= NULL
-- END includes


-- 
-- 
-- 
MsgsPluginToClient ::= SEQUENCE
{
    context INTEGER DEFAULT 0,
    msg     CHOICE
    {
        plugin-text-message                              MsgPluginTextMessage,
        plugin-intelligence-creation                    MsgIntelligenceCreation,
        plugin-intelligence-update                    MsgIntelligenceUpdate,
        plugin-intelligence-destruction                    MsgIntelligenceDestruction,
        
        plugin-limit-creation                                      MsgLimitCreation,
        plugin-limit-update                                        MsgLimitUpdate,
        plugin-limit-destruction                                 MsgLimitDestruction
    }
}

END
