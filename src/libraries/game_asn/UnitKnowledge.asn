--
-- file name : UnitKnowledge.asn
--
-- Messages de gestion de la connaissance d'une unité
--

UnitKnowledge DEFINITIONS AUTOMATIC TAGS ::= BEGIN

-- BEGIN includes
IMPORTS BaseExports FROM Base;
UnitKnowledgeIncludes ::= SEQUENCE { BaseExports }
UnitKnowledgeExports  ::= NULL
-- END includes

MsgUnitKnowledgeCreation ::= SEQUENCE
{
    oid                     UnitKnowledge,   -- id de la connaissance
    oid-groupe-possesseur   KnowledgeGroup,   -- id du groupe de connaissance qui possède cette connaissance
    oid-unite-reelle        Unit,            -- id de l'unité réélle pointée par la connaissance
    type-unite              UnitType
}

AutomatPerception ::= SEQUENCE
{
    oid-compagnie           Automat,
    identification-level    EnumUnitIdentificationLevel
}

MsgUnitKnowledgeUpdate ::= SEQUENCE
{
    oid                         UnitKnowledge,
    oid-groupe-possesseur       KnowledgeGroup,

    pertinence                  Percentage                     OPTIONAL,
    identification-level        EnumUnitIdentificationLevel    OPTIONAL,
    max-identification-level    EnumUnitIdentificationLevel    OPTIONAL,
    etat-op                     FreePercentage                 OPTIONAL,
    mort                        BOOLEAN                        OPTIONAL,
    position                    CoordLatLong                       OPTIONAL,
    direction                   Heading                        OPTIONAL,
    speed                       Speed                          OPTIONAL,
    camp                        OID                            OPTIONAL,
    nature-pc                   BOOLEAN                        OPTIONAL,
    perception-par-compagnie    SEQUENCE OF AutomatPerception  OPTIONAL,
    rendu                       Team                           OPTIONAL, -- '0' quand pas rendu
    prisonnier                  BOOLEAN                        OPTIONAL,
    refugie-pris-en-compte      BOOLEAN                        OPTIONAL
}

MsgUnitKnowledgeDestruction ::= SEQUENCE
{
    oid                     UnitKnowledge,
    oid-groupe-possesseur   KnowledgeGroup
}

END -- UnitKnowledge
