--
-- file name : Notes.asn
--
-- Notes related messages
--

Notes DEFINITIONS AUTOMATIC TAGS ::= BEGIN

-- BEGIN includes
IMPORTS BaseExports FROM Base;
NotesIncludes ::= SEQUENCE { BaseExports }
NotesExports  ::= NULL
-- END includes

Note ::= SEQUENCE
{
    name VisibleString,
    number	VisibleString,
    description VisibleString,
    parent OID
}

MsgNoteCreation ::= SEQUENCE
{
    id OID,
	note Note
}

MsgNoteUpdate ::= SEQUENCE
{
    id OID,
    name VisibleString OPTIONAL,
    number	VisibleString OPTIONAL,
    description VisibleString OPTIONAL,
    parent OID OPTIONAL
}

MsgNoteDestruction ::= SEQUENCE
{
	id OID
}

MsgNoteCreationRequest ::= SEQUENCE
{
    note	   Note
}

MsgNoteUpdateRequest ::= SEQUENCE
{
    id OID,
    name VisibleString OPTIONAL,
    number	VisibleString OPTIONAL,
    description VisibleString OPTIONAL,
    parent OID OPTIONAL
}

MsgNoteDestructionRequest ::= SEQUENCE
{
    id    OID,
    deleteAll BOOLEAN
}

END --  Notes
