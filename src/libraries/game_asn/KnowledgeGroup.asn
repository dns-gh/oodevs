--
-- file name : AutomatetAttr.asn
--
-- Messages de gestion des attributs d'une unité
--

KnowledgeGroup DEFINITIONS AUTOMATIC TAGS ::= BEGIN

-- BEGIN includes
IMPORTS BaseExports FROM Base;
KnowledgeGroupIncludes ::= SEQUENCE { BaseExports }
KnowledgeGroupExports  ::= NULL
-- END includes

MsgKnowledgeGroupCreation ::= SEQUENCE
{
    oid                         KnowledgeGroup,
    oid-camp                    Team,
-- LTO begin
    oid-knowledgegroup-parent   KnowledgeGroup OPTIONAL,
    type                        KnowledgeGroupType
}

MsgKnowledgeGroupUpdate ::= SEQUENCE
{
    oid                         KnowledgeGroup,
    oid-knowledgegroup-parent   KnowledgeGroup OPTIONAL,
    enabled                     BOOLEAN,
    type                        KnowledgeGroupType
}

MsgKnowledgeGroupDelete ::= SEQUENCE
{
    oid                         KnowledgeGroup
}

MsgKnowledgeGroupEnable ::= SEQUENCE
{
    oid                         KnowledgeGroup,
    enabled                     BOOLEAN                                 
}

MsgKnowledgeGroupSetType ::= SEQUENCE
{
    oid                         KnowledgeGroup,
    type                        KnowledgeGroupType
}

MsgKnowledgeGroupChangeSuperior ::= SEQUENCE
{
    oid                         KnowledgeGroup,
    oid-camp                    Team,
    oid-knowledgegroup-parent   KnowledgeGroup
}


EnumKnowledgeGroupErrorCode ::= ENUMERATED
{
    no-error                          (0),
    error-invalid-unit                (1),
    error-invalid-superior            (2),
    error-invalid-camp                (3),
    error-invalid-knowledgegroup      (4),
    error-invalid-type                (5)
}

MsgKnowledgeGroupChangeSuperiorAck ::= SEQUENCE
{
    oid         OID,
    error-code  EnumKnowledgeGroupErrorCode
}

MsgKnowledgeGroupDeleteAck ::= SEQUENCE
{
    oid         OID,
    error-code  EnumKnowledgeGroupErrorCode
}

MsgKnowledgeGroupSetTypeAck ::= SEQUENCE
{
    oid         OID,
    error-code  EnumKnowledgeGroupErrorCode
}

MsgKnowledgeGroupCreationAck ::= SEQUENCE
{
    oid         OID,
    error-code  EnumKnowledgeGroupErrorCode
}
-- LTO end

END -- KnowledgeGroup
