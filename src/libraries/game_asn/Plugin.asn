--
-- file name : Plugin.asn
--
-- Messages provenant d'un plug-in Sword
--

Plugin DEFINITIONS AUTOMATIC TAGS ::= BEGIN

-- BEGIN includes
IMPORTS BaseExports FROM Base
        ArmyExports FROM Army
        IntelligenceExports FROM Intelligence,
        LimaLimiteExports             FROM LimaLimite;
PluginIncludes ::= SEQUENCE { BaseExports, ArmyExports, IntelligenceExports, LimaLimiteExports }
PluginExports  ::= NULL
-- END includes

MsgPluginTextMessage ::= SEQUENCE
{
    destinataire                     VisibleString ,    
    message                     VisibleString          
}

END -- Plugin
