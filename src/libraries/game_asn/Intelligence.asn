--
-- file name : Intelligence.asn
--
-- Intelligence related messages
--

Intelligence DEFINITIONS AUTOMATIC TAGS ::= BEGIN

-- BEGIN includes
IMPORTS BaseExports FROM Base
        ArmyExports FROM Army;
IntelligenceIncludes ::= SEQUENCE { BaseExports, ArmyExports }
IntelligenceExports  ::= NULL
-- END includes

Intelligence ::= SEQUENCE
{
    name        VisibleString,
    nature      VisibleString,
    level       EnumNatureLevel,
    embarked    BOOLEAN,
    location    CoordLatLong,
    diplomacy   EnumDiplomacy,
    formation   Formation
}

IntelligenceList ::= SEQUENCE OF Intelligence

MsgIntelligenceCreation ::= SEQUENCE
{
    oid          OID,
    intelligence Intelligence
}

MsgIntelligenceUpdate ::= SEQUENCE
{
    oid          OID,
    formation    Formation          OPTIONAL,
    name         VisibleString      OPTIONAL,
    nature       VisibleString      OPTIONAL,
    level        EnumNatureLevel    OPTIONAL,
    embarked     BOOLEAN            OPTIONAL,
    location     CoordLatLong           OPTIONAL,
    diplomacy    EnumDiplomacy      OPTIONAL
}

MsgIntelligenceDestruction ::= SEQUENCE
{
    oid         OID
}

MsgIntelligenceCreationRequest ::= SEQUENCE
{
    intelligence Intelligence
}

MsgIntelligenceUpdateRequest ::= SEQUENCE
{
    oid          OID,
    formation    Formation          OPTIONAL,
    name         VisibleString      OPTIONAL,
    nature       VisibleString      OPTIONAL,
    level        EnumNatureLevel    OPTIONAL,
    embarked     BOOLEAN            OPTIONAL,
    location     CoordLatLong           OPTIONAL,
    diplomacy    EnumDiplomacy      OPTIONAL
}

MsgIntelligenceDestructionRequest ::= SEQUENCE
{
    oid          OID
}

-- Error handling

EnumIntelligenceErrorCode ::= ENUMERATED
{
   no-error                        (0),
   error-invalid-oid               (1),
   error-invalid-geometry          (2),
   error-invalid-formation         (3)
}

MsgIntelligenceCreationRequestAck ::= EnumIntelligenceErrorCode

MsgIntelligenceUpdateRequestAck ::= EnumIntelligenceErrorCode

MsgIntelligenceDestructionRequestAck ::= EnumIntelligenceErrorCode

END -- Intelligence
