--
-- file name : UnitAttr.asn
--
-- Messages de gestion des attributs d'une unité
--


Unit DEFINITIONS AUTOMATIC TAGS ::= BEGIN

-- BEGIN includes
IMPORTS BaseExports FROM Base;
UnitIncludes ::= SEQUENCE { BaseExports }
UnitExports  ::= NULL
-- END includes

LentEquipment ::= SEQUENCE
{
    oid-pion-emprunteur Unit,
    type-equipement     EquipmentType,
    nombre              INTEGER
}

BorrowedEquipment ::= SEQUENCE
{
    oid-pion-preteur Unit,
    type-equipement  EquipmentType,
    nombre           INTEGER
}

-- Personnel
HumanDotations ::= SEQUENCE
{
    rang                         EnumHumanRank,
    nb-total                     INTEGER,
    nb-operationnels             INTEGER,
    nb-morts                     INTEGER,
    nb-blesses                   INTEGER,
    nb-blesses-mentaux           INTEGER,
    nb-contamines-nbc            INTEGER,
    nb-dans-chaine-sante         INTEGER,
    nb-utilises-pour-maintenance INTEGER
}

-- Equipement
EquipmentDotations ::= SEQUENCE
{
    type-equipement            EquipmentType,
    nb-disponibles             INTEGER,
    nb-indisponibles           INTEGER,
    nb-reparables              INTEGER,
    nb-dans-chaine-maintenance INTEGER, -- En réparation
    nb-prisonniers             INTEGER
}

-- NBC
ContaminationState ::= SEQUENCE
{
    percentage      Percentage,
    quantity        REAL    
}

-- Ressources
ResourceDotations ::= SEQUENCE
{
    ressource-id        DotationType,
    quantite-disponible INTEGER
}

EnumUnitTiredness ::= ENUMERATED
{
    normal  (0),
    fatigue (1),
    epuise  (2)
}

EnumUnitMorale ::= ENUMERATED
{
    fanatique(0),
    bon      (1),
    moyen    (2),
    mauvais  (3)
}

EnumUnitExperience ::= ENUMERATED
{
    veteran    (0),
    experimente(1),
    conscrit   (2)
}

EnumUnitPosture ::= ENUMERATED
{
    posture-mouvement           (0),
    posture-mouvement-discret   (1),
    posture-arret               (2),
    posture-poste-reflexe       (3),
    posture-poste               (4),
    posture-poste-amenage       (5),
    posture-poste-prepare-genie (6)
}

EnumForceRatioStatus ::= ENUMERATED
{
    none        (0),
    neutre      (1),
    favorable   (2),
    defavorable (3)
}

EnumRoe ::= ENUMERATED
{
    none           (0),
    tir-libre      (1),
    tir-sur-riposte(2),
    tir-interdit   (3)
}

EnumPopulationRoe ::= ENUMERATED
{
    none                                        (0),
    emploi-force-interdit                       (1),
    maintien-a-distance-par-moyens-non-letaux   (2),
    dispersion-par-moyens-de-defense-actifs     (3),
    armes-letales-autorisees                    (4)
}

EnumMeetingEngagementStatus ::= ENUMERATED
{
    none                  (0),
    etat-esquive          (1),
    etat-fixe             (2),
    etat-poursuite-mission(3)
}

EnumOperationalStatus ::= ENUMERATED
{
    detruit-totalement      (0),
    detruit-tactiquement    (1),
    operationnel            (2)
}

EnumFireAvailability ::= ENUMERATED
{
    none         (0),
    pret-au-tir  (1),
    indisponible (2)
}


MsgUnitCreation ::= SEQUENCE
{
    oid             Unit,
    type-pion       UnitType,
    nom             VisibleString,
    oid-automate    Automat,
    pc              BOOLEAN
}

MsgUnitAttributes ::= SEQUENCE
{
    oid                           Unit,

    dotation-eff-personnel        SEQUENCE OF HumanDotations      OPTIONAL, -- Dotations effectives du pion DELTA
    dotation-eff-materiel         SEQUENCE OF EquipmentDotations  OPTIONAL, -- DELTA // $$$$ AGE 2007-10-16: non, pas du tout DELTA
    dotation-eff-ressource        SEQUENCE OF ResourceDotations   OPTIONAL, -- DELTA // $$$$ AGE 2007-10-16: non, pas du tout DELTA non plus
    equipements-pretes            SEQUENCE OF LentEquipment       OPTIONAL, -- FULL
    equipements-empruntes         SEQUENCE OF BorrowedEquipment   OPTIONAL, -- FULL

    position                      CoordLatLong                        OPTIONAL,
    direction                     Heading                         OPTIONAL, -- en degrés
    hauteur                       Height                          OPTIONAL, -- hauteur d'un pion 3D par rapport au sol en mètres
    altitude                      Height                          OPTIONAL, -- altitude d'un pion 3D par rapport au niveau de la mer
    vitesse                       Speed                           OPTIONAL, -- en km/h
    etat-operationnel-brut        FreePercentage                  OPTIONAL,
    pions-renforcant              UnitList                        OPTIONAL,
    pion-renforce                 Unit                            OPTIONAL, -- '0' quand pas en renfort
    mort                          BOOLEAN                         OPTIONAL,
    neutralise                    BOOLEAN                         OPTIONAL,
    mode-furtif-actif             BOOLEAN                         OPTIONAL,
    embarque                      BOOLEAN                         OPTIONAL,
    transporteurs-disponibles     BOOLEAN                         OPTIONAL,

    posture-old                   EnumUnitPosture                 OPTIONAL,
    posture-new                   EnumUnitPosture                 OPTIONAL,
    posture-pourcentage           Percentage                      OPTIONAL,

    etat-installation             Percentage                      OPTIONAL,

    en-tenue-de-protection-nbc    BOOLEAN                         OPTIONAL,
    contamine-par-agents-nbc      ListOID                         OPTIONAL,          -- ID d'agents chimiques - Cf. MOS/IDClasses.xml
    etat-contamination            ContaminationState              OPTIONAL,

    communications-brouillees     BOOLEAN                         OPTIONAL,
    silence-radio                 BOOLEAN                         OPTIONAL,
    radar-actif                   BOOLEAN                         OPTIONAL,

    pions-transportes             UnitList                        OPTIONAL,
    pion-transporteur             Unit                            OPTIONAL, -- '0' quand aucun transporteur

    rapport-de-force              EnumForceRatioStatus            OPTIONAL,
    combat-de-rencontre           EnumMeetingEngagementStatus     OPTIONAL,
    etat-operationnel             EnumOperationalStatus           OPTIONAL,
    disponibilite-au-tir-indirect EnumFireAvailability            OPTIONAL,
    roe                           EnumRoe                         OPTIONAL,
    roe-population                EnumPopulationRoe               OPTIONAL,

    fatigue                       EnumUnitTiredness               OPTIONAL,
    moral                         EnumUnitMorale                  OPTIONAL,
    experience                    EnumUnitExperience              OPTIONAL,

    rendu                         Team                            OPTIONAL, -- '0' quand pas rendu
    prisonnier                    BOOLEAN                         OPTIONAL,
    refugie-pris-en-compte        BOOLEAN                         OPTIONAL
}

MsgUnitEnvironmentType ::= SEQUENCE
{
    oid         Unit,
    area        INTEGER( 0..255 ),
    left        INTEGER( 0..255 ),
    right       INTEGER( 0..255 ),
    linear      INTEGER( 0..65535 )
}

MsgUnitDestruction ::= OID

-- Actions magiques

MagicActionRecoverTransporters      ::= NULL
MagicActionSurrender                ::= Team
MagicActionCancelRendition          ::= NULL
MagicActionMoveTo                   ::= CoordLatLong    -- Position
MagicActionTotalDestruction         ::= NULL
MagicActionComponentDestruction     ::= NULL
MagicActionTotalRecovery            ::= NULL
MagicActionHumanRecovery            ::= NULL
MagicActionEquipmentRecovery        ::= NULL
MagicActionRessourcesRecovery       ::= NULL
MagicActionChangeHumanFactors       ::= SEQUENCE
{
    fatigue    EnumUnitTiredness  OPTIONAL,
    moral      EnumUnitMorale     OPTIONAL,
    experience EnumUnitExperience OPTIONAL
}

DotationRecovery ::= SEQUENCE
{
    famille-dotation    EnumDotationFamily,
    pourcentage         Percentage
}

AmmunitionDotationRecovery ::= SEQUENCE
{
    famille-munition EnumAmmunitionFamily,
    pourcentage      Percentage
}

EquipmentRecovery ::= SEQUENCE
{
    type-equipement   EquipmentType,
    nombre-disponible INTEGER
}

HumanRecovery ::= SEQUENCE
{
    rang              EnumHumanRank,
    nombre-disponible INTEGER
}

StockRecovery ::= SEQUENCE
{
    ressource-id        DotationType,
    quantite-disponible INTEGER
}

MagicActionPartialRecovery ::= SEQUENCE
{
    equipements SEQUENCE OF EquipmentRecovery          OPTIONAL,
    personnels  SEQUENCE OF HumanRecovery              OPTIONAL,
    dotations   SEQUENCE OF DotationRecovery           OPTIONAL,
    munitions   SEQUENCE OF AmmunitionDotationRecovery OPTIONAL,
    stocks      SEQUENCE OF StockRecovery              OPTIONAL
}

MsgUnitMagicAction ::= SEQUENCE
{
    oid     OID,  -- oid de l'unité
    action  CHOICE
    {
        move-to                     MagicActionMoveTo,
        recompletement-total        MagicActionTotalRecovery,
        recompletement-partiel      MagicActionPartialRecovery,
        recompletement-personnel    MagicActionHumanRecovery,
        recompletement-equipement   MagicActionEquipmentRecovery,
        recompletement-ressources   MagicActionRessourcesRecovery,
        change-facteurs-humains     MagicActionChangeHumanFactors,
        destruction-totale          MagicActionTotalDestruction,
        destruction-composante      MagicActionComponentDestruction,
        se-rendre                   MagicActionSurrender,
        annuler-reddition           MagicActionCancelRendition,
        recuperer-transporteurs     MagicActionRecoverTransporters
    }
}

EnumUnitErrorCode ::= ENUMERATED
{
    no-error                (0),
    error-invalid-unit      (1),
    error-automate-embraye  (2),
    error-invalid-attribute (3),
    error-unit-surrendered  (4)
}

MsgUnitMagicActionAck ::= SEQUENCE
{
    oid         OID,
    error-code  EnumUnitErrorCode
}

MsgUnitCreationRequest ::= SEQUENCE
{
    type-pion       UnitType,
    oid-automate    Automat,
    position        CoordLatLong
}
MsgUnitCreationRequestAck ::= EnumUnitErrorCode
MsgUnitChangeSuperiorAck  ::= EnumChangeHierarchyErrorCode

MsgUnitPathFind ::= SEQUENCE
{
    oid         OID,
    itineraire  Path
}

MsgUnitChangeSuperior ::= SEQUENCE
{
    oid          Unit,
    oid-automate Automat
}

VisionCone ::= SEQUENCE
{
    origin       CoordLatLong,
    height       Height,
    sensor       VisibleString,
    directions   SEQUENCE OF Heading
}

MsgUnitVisionCones ::= SEQUENCE
{
    oid          Unit,
    cones        SEQUENCE OF VisionCone,
    elongation   REAL
}

MsgUnitDetection ::= SEQUENCE
{
    oid                 Unit,
    detected-unit-oid   Unit,
    current-visibility  EnumUnitVisibility,
    max-visibility      EnumUnitVisibility
}

MsgObjectDetection ::= SEQUENCE
{
    oid        Unit,
    object-oid OID,
    visibility EnumUnitVisibility
}

MsgUrbanDetection ::= SEQUENCE
{
    oid        Unit,
    urban-oid  OID,
    visibility EnumUnitVisibility
}

MsgPopulationConcentrationDetection ::= SEQUENCE
{
    oid                 Unit,
    population-oid      OID,
    concentration-oid   OID,
    visibility          EnumUnitVisibility
}

MsgPopulationFlowDetection ::= SEQUENCE
{
    oid            Unit,
    population-oid OID,
    flow-oid       OID,
    visible-flow   Path
}

END -- Unit
