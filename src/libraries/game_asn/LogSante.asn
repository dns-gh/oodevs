--
-- file name : LogSante.asn
--
-- Messages de gestion des attributs d'une unité
--


LogSante DEFINITIONS AUTOMATIC TAGS ::= BEGIN

-- BEGIN includes
IMPORTS BaseExports FROM Base;
LogSanteIncludes ::= SEQUENCE { BaseExports }
LogSanteExports  ::= NULL
-- END includes

EnumLogMedicalHandlingStatus ::= ENUMERATED
{ 
    attente-disponibilite-ambulance-releve          (0),
    ambulance-releve-deplacement-aller              (1),
    ambulance-releve-chargement                     (2),
    attente-chargement-complet-ambulance-releve     (3),
    ambulance-releve-deplacement-retour             (4),
    ambulance-releve-dechargement                   (5),
    attente-disponibilite-medecin-pour-diagnostique (6),
    diagnostique                                    (7),
    recherche-secteur-tri                           (8),
    attente-disponibilite-medecin-pour-tri          (9),
    tri                                             (10),
    recherche-secteur-soin                          (11),
    attente-disponibilite-medecin-pour-soin         (12),
    soin                                            (13),
    hospitalisation                                 (14),
    attente-disponibilite-ambulance-ramassage       (15),
    ambulance-ramassage-chargement                  (16),
    attente-chargement-complet-ambulance-ramassage  (17),
    ambulance-ramassage-deplacement-aller           (18),
    ambulance-ramassage-dechargement                (19),
    termine                                         (20)
}

MsgLogMedicalHandlingCreation ::= SEQUENCE
{
    oid-consigne    OID,
    oid-pion        Unit,          -- pion possèdant l'Humain    
    tick-creation   INTEGER,
    rang            EnumHumanRank,
    blessure        EnumHumanWound,
    blesse-mental   BOOLEAN DEFAULT FALSE,
    contamine-nbc   BOOLEAN DEFAULT FALSE    
}

MsgLogMedicalHandlingUpdate ::= SEQUENCE
{
    oid-consigne          OID,
    oid-pion              Unit,          -- pion possèdant l'Humain
    oid-pion-log-traitant Unit                      OPTIONAL,          -- pion LOG gérant le traitement de l'humain, 0 si aucun pion (demande passée à la BLIAT par exemple)
    blessure              EnumHumanWound             OPTIONAL,
    blesse-mental         BOOLEAN                    OPTIONAL,
    contamine-nbc         BOOLEAN                    OPTIONAL,
    etat                  EnumLogMedicalHandlingStatus OPTIONAL,
    diagnostique-effectue BOOLEAN                    OPTIONAL    
}

MsgLogMedicalHandlingDestruction ::= SEQUENCE
{
    oid-consigne    OID,
    oid-pion        Unit -- pion possèdant l'Humain    
}

-- Etat des pions logistiques de la santé
LogMedicalEquipmentAvailability ::= SEQUENCE
{
    type-equipement  EquipmentType,
    nbr-total        INTEGER,
    nbr-disponibles  INTEGER,       
    nbr-au-travail   INTEGER,
    nbr-pretes       INTEGER DEFAULT 0,
    nbr-au-repos     INTEGER OPTIONAL -- applicable uniquement à certains moyens
}

LogMedicalPriorities ::= SEQUENCE OF EnumHumanWound

MsgLogMedicalState ::= SEQUENCE
{
    oid-pion                               Unit,
    chaine-activee                         BOOLEAN                              OPTIONAL,
    priorites                              LogMedicalPriorities                       OPTIONAL,
    priorites-tactiques                    AutomatList                         OPTIONAL,
    disponibilites-ambulances-releve       SEQUENCE OF LogMedicalEquipmentAvailability OPTIONAL,
    disponibilites-ambulances-ramassage    SEQUENCE OF LogMedicalEquipmentAvailability OPTIONAL,
    disponibilites-medecins                SEQUENCE OF LogMedicalEquipmentAvailability OPTIONAL
}

END -- LogSante
