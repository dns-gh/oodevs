--
-- file name : Population.asn
--
-- Messages de gestion des objets
--

Population DEFINITIONS AUTOMATIC TAGS ::= BEGIN

-- BEGIN includes
IMPORTS BaseExports FROM Base;
PopulationIncludes ::= SEQUENCE { BaseExports }
PopulationExports  ::= NULL
-- END includes

EnumPopulationAttitude ::= ENUMERATED
{
    calme     (0),
    agitee    (1),
    excitee   (2),
    agressive (3)
}

-------------------
-- Population
-------------------

MsgPopulationCreation ::= SEQUENCE
{
    oid             OID,
    type-population PopulationType,
    nom             VisibleString,
    oid-camp        OID    
}

MsgPopulationUpdate ::= SEQUENCE
{
    oid             OID,
    etat-domination Percentage OPTIONAL
}

-------------------
-- Concentration
-------------------

MsgPopulationConcentrationCreation ::= SEQUENCE
{
    oid               OID,
    oid-population    OID,
    position          CoordLatLong
}

MsgPopulationConcentrationUpdate ::= SEQUENCE
{
    oid                 OID,
    oid-population      OID,
    
    nb-humains-vivants  INTEGER                OPTIONAL,
    nb-humains-morts    INTEGER                OPTIONAL,
    attitude            EnumPopulationAttitude OPTIONAL
}

MsgPopulationConcentrationDestruction ::= SEQUENCE
{
    oid               OID,
    oid-population    OID
}

-------------------
-- Flux
-------------------

MsgPopulationFlowCreation ::= SEQUENCE
{
    oid             OID,
    oid-population  OID
}

MsgPopulationFlowUpdate ::= SEQUENCE
{
    oid                 OID,
    oid-population      OID,
    itineraire          Path             OPTIONAL, -- Path de la tête
    flux                Path             OPTIONAL,
    direction           Heading              OPTIONAL, -- en degres
    vitesse             Speed                OPTIONAL, -- en km/h
    nb-humains-vivants  INTEGER                OPTIONAL,
    nb-humains-morts    INTEGER                OPTIONAL,
    attitude            EnumPopulationAttitude OPTIONAL
}

MsgPopulationFlowDestruction ::= SEQUENCE
{
    oid             OID,
    oid-population  OID
}

---------------------------
-- Actions magiques
---------------------------

MagicActionPopulationChangeAttitude ::= SEQUENCE
{
    attitude        EnumPopulationAttitude, -- nouvelle attitude
    beneficiaire    CHOICE                  -- cible
    {
        flux            OID,
        concentration   OID,
        global          NULL
    }
}

MagicActionPopulationMoveTo             ::= CoordLatLong    -- Position
MagicActionPopulationTotalDestruction   ::= NULL
MagicActionPopulationKill               ::= INTEGER     -- nombre de personne tuées
MagicActionPopulationResurrect          ::= INTEGER     -- nombre de personne ressuscitées

MsgPopulationMagicAction ::= SEQUENCE
{
    oid             OID,  -- oid de l'entité population
    action          CHOICE
    {       
        change-attitude    MagicActionPopulationChangeAttitude,
        move-to            MagicActionPopulationMoveTo,
        destruction-totale MagicActionPopulationTotalDestruction,
        tuer               MagicActionPopulationKill,
        ressusciter        MagicActionPopulationResurrect
    }       
}

EnumPopulationErrorCode ::= ENUMERATED
{
    no-error                (0),
    error-invalid-unit      (1),
    error-invalid-attribute (2)
}

MsgPopulationMagicActionAck ::= SEQUENCE
{
    oid         OID,
    error-code  EnumPopulationErrorCode
}

END -- Population
