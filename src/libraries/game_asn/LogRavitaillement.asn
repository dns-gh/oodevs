--
-- file name : LogRavitaillement.asn
--
-- Messages de gestion de la chaine logistique ravitaillement
--

LogRavitaillement DEFINITIONS AUTOMATIC TAGS ::= BEGIN

-- BEGIN includes
IMPORTS BaseExports FROM Base;
LogRavitaillementIncludes ::= SEQUENCE { BaseExports }
LogRavitaillementExports  ::= NULL
-- END includes

DotationQuery ::= SEQUENCE
{
    ressource-id        DotationType,
    quantite-demandee   INTEGER,
    quantite-accordee   INTEGER,
    quantite-en-transit INTEGER
}

MsgLogSupplyHandlingCreation ::= SEQUENCE
{
    oid-consigne    OID,
    oid-automate    Automat,  
    tick-creation   INTEGER,
    dotations       SEQUENCE OF DotationQuery
}

EnumLogSupplyHandlingStatus ::= ENUMERATED
{ 
    convoi-en-attente-camions                   (0),
    convoi-constitution                         (1),
    convoi-deplacement-vers-point-chargement    (2),
    convoi-chargement                           (3),
    convoi-deplacement-vers-point-dechargement  (4),
    convoi-dechargement                         (5),
    convoi-deplacement-retour                   (6),
    termine                                     (7)
}

MsgLogSupplyHandlingUpdate ::= SEQUENCE
{
    oid-consigne                                OID,
    oid-automate                                Automat,                                     -- automate demandeur
    oid-automate-log-traitant                   Automat                            OPTIONAL, -- automate LOG gérant le ravitaillement, 0 si aucun automate
    oid-automate-log-fournissant-moyens-convoi  Automat                            OPTIONAL, -- automate LOG fournissant les moyens de constitution des convois
    oid-pion-convoyant                          Unit                               OPTIONAL, -- pion LOG convoyant le rav
    etat                                        EnumLogSupplyHandlingStatus OPTIONAL,
    dotations                                   SEQUENCE OF DotationQuery         OPTIONAL
}

MsgLogSupplyHandlingDestruction ::= SEQUENCE
{
    oid-consigne    OID,
    oid-automate    Automat
}

-- Etat des pions logistiques du ravitaillement
LogSupplyEquimentAvailability ::= SEQUENCE
{
    type-equipement  EquipmentType,
    nbr-total        INTEGER,
    nbr-disponibles  INTEGER,       
    nbr-au-travail   INTEGER,
    nbr-pretes       INTEGER DEFAULT 0,
    nbr-au-repos     INTEGER OPTIONAL -- applicable uniquement à certains moyens
}

DotationStock ::= SEQUENCE 
{
    ressource-id        DotationType,
    quantite-disponible INTEGER
}

MsgLogSupplyState ::= SEQUENCE
{
    oid-pion                             Unit,    
    chaine-activee                       BOOLEAN                                       OPTIONAL,
    stocks                               SEQUENCE OF DotationStock                     OPTIONAL, -- Seules les dotations qui ont changées sont envoyées
    disponibilites-transporteurs-convois SEQUENCE OF LogSupplyEquimentAvailability OPTIONAL
}

DotationQuota ::= SEQUENCE
{
    ressource-id        DotationType,
    quota-disponible    INTEGER
}

MsgLogSupplyChangeQuotas ::= SEQUENCE
{
    oid-donneur  Automat,
    oid-receveur Automat,
    quotas       SEQUENCE OF DotationQuota -- Tous les quotas sont envoyés, même ceux dont la valeur n'a pas changé
}
MsgLogSupplyChangeQuotasAck ::= ENUMERATED
{
    no-error              (0),
    error-invalid-donneur (1),
    error-invalid-receveur(2)
}

MsgLogSupplyPushFlow ::= SEQUENCE
{
    oid-donneur  Automat,
    oid-receveur Automat,
    stocks       SEQUENCE OF DotationStock
}
MsgLogSupplyPushFlowAck ::= ENUMERATED
{
    no-error              (0),
    error-invalid-donneur (1),
    error-invalid-receveur(2)
}
   
MsgLogSupplyQuotas ::= SEQUENCE
{
    oid-automate  Automat,
    quotas        SEQUENCE OF DotationQuota -- Tous est envoyé
}

END -- LogRavitaillement
