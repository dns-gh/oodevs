--
-- file name : ScipioUnitAttr.asn
--
-- Messages de gestion des attributs d'une unité
--


ScipioUnit DEFINITIONS AUTOMATIC TAGS ::= BEGIN

EquipementPrete ::= SEQUENCE
{
    oid-pion-emprunteur Agent,
    type-equipement     TypeEquipement,
    nombre              INTEGER
}

EquipementEmprunte ::= SEQUENCE
{
    oid-pion-preteur Agent,
    type-equipement  TypeEquipement,
    nombre           INTEGER
}

-- Personnel
DotationPersonnel ::= SEQUENCE 
{
    rang                         EnumHumanRank,
    nb-total                     INTEGER, 
    nb-operationnels             INTEGER, 
    nb-morts                     INTEGER, 
    nb-blesses                   INTEGER, 
    nb-blesses-mentaux           INTEGER, 
    nb-contamines-nbc            INTEGER,
    nb-dans-chaine-sante         INTEGER,
    nb-utilises-pour-maintenance INTEGER
}

-- Equipement
DotationEquipement ::= SEQUENCE
{
    type-equipement            TypeEquipement,
    nb-disponibles             INTEGER,
    nb-indisponibles           INTEGER,
    nb-reparables              INTEGER,
    nb-dans-chaine-maintenance INTEGER, -- En réparation
    nb-prisonniers             INTEGER
}

-- Ressources
DotationRessource ::= SEQUENCE 
{
    ressource-id        TypeDotation,
    quantite-disponible INTEGER
}

EnumUnitFatigue ::= ENUMERATED
{
    normal  (0),
    fatigue (1),
    epuise  (2)  
}

EnumUnitMoral ::= ENUMERATED
{
    fanatique(0),
    bon      (1),
    moyen    (2),
    mauvais  (3)
}

EnumUnitExperience ::= ENUMERATED
{
    veteran    (0),
    experimente(1),
    conscrit   (2)
}

EnumUnitPosture ::= ENUMERATED
{
    posture-mouvement           (0),
    posture-mouvement-discret   (1),
    posture-arret               (2),
    posture-poste-reflexe       (3),
    posture-poste               (4),
    posture-poste-amenage       (5),
    posture-poste-prepare-genie (6)
}

EnumEtatRapFor ::= ENUMERATED
{
    none        (0),
    neutre      (1),
    favorable   (2),
    defavorable (3)
}

EnumRoe ::= ENUMERATED
{
    none           (0),       
    tir-libre      (1),
    tir-sur-riposte(2),
    tir-interdit   (3)
}

EnumRoePopulation ::= ENUMERATED
{
    none                                        (0),
    emploi-force-interdit                       (1),
    maintien-a-distance-par-moyens-non-letaux   (2),
    dispersion-par-moyens-de-defense-actifs     (3),
    armes-letales-autorisees                    (4)
}

EnumEtatCombatRencontre ::= ENUMERATED
{
    none                  (0),
    etat-esquive          (1),
    etat-fixe             (2),
    etat-poursuite-mission(3)               
}

EnumEtatOperationnel ::= ENUMERATED
{
    detruit-totalement      (0),
    detruit-tactiquement    (1),
    operationnel            (2)
}

EnumDisponibiliteAuTir ::= ENUMERATED
{
    none         (0),
    pret-au-tir  (1),
    indisponible (2)
}


MsgPionCreation ::= SEQUENCE
{
    oid-pion        Agent,
    type-pion       TypePion,
    nom             VisibleString,
    oid-automate    Automate,
    pc              BOOLEAN
}

MsgUnitAttributes ::= SEQUENCE
{
    oid-pion                      Agent,
    
    dotation-eff-personnel        SEQUENCE OF DotationPersonnel     OPTIONAL, -- Dotations effectives du pion DELTA
    dotation-eff-materiel         SEQUENCE OF DotationEquipement    OPTIONAL, -- DELTA
    dotation-eff-ressource        SEQUENCE OF DotationRessource     OPTIONAL, -- DELTA
    equipements-pretes            SEQUENCE OF EquipementPrete       OPTIONAL, -- FULL
    equipements-empruntes         SEQUENCE OF EquipementEmprunte    OPTIONAL, -- FULL
        
    position				      CoordUTM                          OPTIONAL,
    direction                     Direction                         OPTIONAL, -- en degrés
    hauteur                       Hauteur                           OPTIONAL, -- hauteur d'un pion 3D par rapport au sol en mètres
    vitesse                       Vitesse                           OPTIONAL, -- en km/h
    etat-operationnel-brut        PourcentageLibre                  OPTIONAL,
    pions-renforcant              ListAgent                         OPTIONAL,
    pion-renforce                 Agent                             OPTIONAL, -- '0' quand pas en renfort
    mort                          BOOLEAN                           OPTIONAL,   
    neutralise                    BOOLEAN                           OPTIONAL,   
    mode-furtif-actif             BOOLEAN                           OPTIONAL,
    embarque                      BOOLEAN                           OPTIONAL,
    transporteurs-disponibles     BOOLEAN                           OPTIONAL,
    
    posture-old                   EnumUnitPosture                   OPTIONAL,
    posture-new                   EnumUnitPosture                   OPTIONAL,
    posture-pourcentage           Pourcentage                       OPTIONAL,
    
    etat-installation             Pourcentage                       OPTIONAL,
                                                                    
    en-tenue-de-protection-nbc    BOOLEAN                           OPTIONAL,
    contamine-par-agents-nbc      ListOID                           OPTIONAL,          -- ID d'agents chimiques - Cf. MOS/IDClasses.xml
    etat-contamination            Pourcentage                       OPTIONAL,
    
    communications-brouillees     BOOLEAN                           OPTIONAL,
    silence-radio                 BOOLEAN                           OPTIONAL,
    radar-actif                   BOOLEAN                           OPTIONAL,
    
    pions-transportes             ListAgent                         OPTIONAL, 
    pion-transporteur             Agent                             OPTIONAL, -- '0' quand aucun transporteur
    
    rapport-de-force              EnumEtatRapFor                    OPTIONAL,
    combat-de-rencontre           EnumEtatCombatRencontre           OPTIONAL,
    etat-operationnel             EnumEtatOperationnel              OPTIONAL,
    disponibilite-au-tir-indirect EnumDisponibiliteAuTir            OPTIONAL,
    roe                           EnumRoe                           OPTIONAL,
    roe-population                EnumRoePopulation                 OPTIONAL,
    
    fatigue                       EnumUnitFatigue                   OPTIONAL,
    moral                         EnumUnitMoral                     OPTIONAL,
    experience                    EnumUnitExperience                OPTIONAL,
    
    rendu                         BOOLEAN                           OPTIONAL,
    prisonnier                    BOOLEAN                           OPTIONAL,
    refugie-pris-en-compte        BOOLEAN                           OPTIONAL
}

-- Actions magiques

MagicActionRecupererTransporteurs   ::= NULL
MagicActionSeRendre                 ::= NULL        
MagicActionMoveTo                   ::= CoordUTM    -- Position
MagicActionDestructionTotale        ::= NULL
MagicActionRecompletementTotal      ::= NULL
MagicActionRecompletementPersonnel  ::= NULL
MagicActionRecompletementEquipement ::= NULL
MagicActionRecompletementRessources ::= NULL
MagicActionChangeFacteursHumains    ::= SEQUENCE
{
    fatigue    EnumUnitFatigue    OPTIONAL,
    moral      EnumUnitMoral      OPTIONAL,
    experience EnumUnitExperience OPTIONAL
}

RecompletementDotation ::= SEQUENCE
{
    famille-dotation    EnumFamilleDotation,
    pourcentage         Pourcentage
}

RecompletementDotationMunition ::= SEQUENCE
{
    famille-munition EnumFamilleMunition,
    pourcentage      Pourcentage
}

RecompletementEquipement ::= SEQUENCE
{
    type-equipement   TypeEquipement,
    nombre-disponible INTEGER
}

RecompletementPersonnel ::= SEQUENCE
{
    rang              EnumHumanRank,
    nombre-disponible INTEGER
}

RecompletementStock ::= SEQUENCE
{
    ressource-id        TypeDotation,
    quantite-disponible INTEGER
}

MagicActionRecompletementPartiel ::= SEQUENCE
{
    equipements SEQUENCE OF RecompletementEquipement        OPTIONAL,
    personnels  SEQUENCE OF RecompletementPersonnel         OPTIONAL,    
    dotations   SEQUENCE OF RecompletementDotation          OPTIONAL,
    munitions   SEQUENCE OF RecompletementDotationMunition  OPTIONAL,
    stocks      SEQUENCE OF RecompletementStock             OPTIONAL
}

MsgUnitMagicAction ::= SEQUENCE
{
    oid         OID,  -- oid de l'unité
    action  CHOICE
    {
        move-to                     MagicActionMoveTo,
        recompletement-total        MagicActionRecompletementTotal,
        recompletement-partiel      MagicActionRecompletementPartiel,
        recompletement-personnel    MagicActionRecompletementPersonnel,
        recompletement-equipement   MagicActionRecompletementEquipement,
        recompletement-ressources   MagicActionRecompletementRessources,
        change-facteurs-humains     MagicActionChangeFacteursHumains,
        destruction-totale          MagicActionDestructionTotale,
        se-rendre                   MagicActionSeRendre,
        recuperer-transporteurs     MagicActionRecupererTransporteurs
    }       
}

EnumUnitAttrErrorCode ::= ENUMERATED
{
    no-error                (0),
    error-invalid-unit      (1),
    error-automate-embraye  (2),
    error-invalid-attribute (3),
    error-unit-surrendered  (4)
}

MsgUnitMagicActionAck ::= SEQUENCE
{
    oid         OID,
    error-code  EnumUnitAttrErrorCode
}

-- Path finder
MsgUnitPathFind ::= SEQUENCE
{
    oid-pion    OID,
    itineraire  Itineraire
}

END -- ScipioUnit
