--
-- file name : Messages.asn
--
-- Messages list
--

Messages DEFINITIONS AUTOMATIC TAGS ::= BEGIN

-- BEGIN includes
IMPORTS ProfilesExports  FROM Profiles
        ExercisesExports FROM Exercises
        GamesExports     FROM Games;
MessagesIncludes ::= SEQUENCE { ProfilesExports, ExercisesExports, GamesExports }
MessagesExports  ::= NULL
-- END includes

MsgClientAnnouncement ::= NULL

MsgsInMaster ::= SEQUENCE
{
    context INTEGER DEFAULT 0,
    msg     CHOICE
    {
        msg-client-announcement     MsgClientAnnouncement,
    
        -- profiles
        msg-authentication-request  MsgAuthenticationRequest,
        -- exercises
        msg-exercise-list-request   MsgExerciseListRequest,
        -- games
        msg-game-start-request      MsgGameStartRequest,
        msg-game-stop-request       MsgGameStopRequest
    }
}

MsgsOutMaster ::= SEQUENCE
{
    context INTEGER DEFAULT 0,
    msg     CHOICE
    {
        -- profiles
        msg-authentication-response MsgAuthenticationResponse,
        -- exercises
        msg-exercise-list-response  MsgExerciseListResponse,
        -- games
        msg-game-start-response     MsgGameStartResponse,
        msg-game-stop-response      MsgGameStopResponse
    }
}

END
