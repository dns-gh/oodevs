--
-- file name : ScipioObject.asn
--
-- Messages de gestion des objets
--

ScipioObject DEFINITIONS AUTOMATIC TAGS ::= BEGIN

-- BEGIN includes
IMPORTS ScipioBaseExports FROM ScipioBase;
ScipioObjectIncludes ::= SEQUENCE { ScipioBaseExports }
ScipioObjectExports  ::= NULL
-- END includes

EnumMissionGenSousTypeObstacle ::= ENUMERATED
{
    preliminaire(0),
    de-manoeuvre(1)
}

EnumObjectType ::= ENUMERATED
{
    bouchon-mines               (0),
    zone-minee-lineaire         (1),
    zone-minee-par-dispersion   (2),
    fosse-anti-char             (3),
    abattis                     (4),
    barricade                   (5),
    eboulement                  (6),
    destruction-route           (7),
    destruction-pont            (8),
    pont-flottant-continu       (9), 
    poste-tir                   (10),
    zone-protegee               (11),
    zone-implantation-canon     (12),
    zone-implantation-cobra     (13),
    zone-implantation-lrm       (14),
    site-franchissement         (15),
    nuage-nbc                   (16), -- Doit etre une localisation de type 'cercle'
    plot-ravitaillement         (17),
    site-decontamination        (18),
    zone-brouillage-brod        (19),
    rota                        (20),
    zone-nbc                    (21), -- Doit etre une localisation de type 'cercle'
    zone-brouillage-bromure     (22),
    aire-poser                  (23),
    piste                       (24),
    plateforme                  (25),
    zone-mobilite-amelioree     (26),
    zone-poser-helicoptere      (27),
    aire-logistique             (28),
    itineraire-logistique       (29), -- Doit etre une localisation de type 'ligne'
    camp-prisonniers            (30),
    camp-refugies               (31),
    poste-controle              (32),
    terrain-largage             (33),
    zone-interdite-mouvement    (34),
    zone-interdite-tir          (35),
    zone-implantation-mortier   (36),
    pont-flottant-discontinu    (37),
    installation                (38)
}

EnumObjectErrorCode ::= ENUMERATED
{
    no-error                         (0),
    error-invalid-object             (1),
    error-invalid-id                 (2),
    error-invalid-camp               (3),
    error-invalid-localisation       (4),
    error-missing-specific-attributes(5),
    error-invalid-specific-attributes(6)
}


---------------------------
-- Attributs specifiques a certains objets
---------------------------     
AttrObjectSiteFranchissement ::= SEQUENCE
{
    largeur             INTEGER,    -- en mètres
    profondeur          INTEGER,    -- en mètres
    vitesse-courant     INTEGER,    -- en m/s
    berges-a-amenager   BOOLEAN
}

AttrObjectNuageNBC ::= SEQUENCE
{
    agent-nbc OID -- Cf. Data/NBC.xml
}

AttrObjectZoneNBC ::= SEQUENCE
{
    agent-nbc OID -- Cf. Data/NBC.xml
}

AttrObjectROTA ::= SEQUENCE
{
    niveau-danger       INTEGER(0..10),
    agents-nbc          ListOID -- Cf. Data/NBC.xml
}

AttrObjectItineraireLogistique ::= SEQUENCE
{
    itineraire-equipe   BOOLEAN,
    poids-max-supporte  INTEGER,
    largeur             INTEGER,
    longueur            INTEGER,
    debit               INTEGER
}

AttrObjectCampPrisonniers ::= SEQUENCE
{
    tc2  Automate
}

AttrObjectCampRefugies ::= SEQUENCE
{
    tc2  Automate
}

AttrObjectSpecific ::= CHOICE
{
    site-franchissement   AttrObjectSiteFranchissement,
    nuage-nbc             AttrObjectNuageNBC,
    rota                  AttrObjectROTA,
    zone-nbc              AttrObjectZoneNBC,
    itineraire-logistique AttrObjectItineraireLogistique,
    camp-prisonniers      AttrObjectCampPrisonniers,
    camp-refugies         AttrObjectCampRefugies
}
 
---------------------------
-- Objet réel
---------------------------     

MsgObjectCreation ::= SEQUENCE
{
    oid                         OID,
    type                        EnumObjectType,
    localisation                Localisation,
    nom                         VisibleString,
    camp                        Camp,
    attributs-specifiques       AttrObjectSpecific OPTIONAL,
    type-dotation-construction  TypeDotation       OPTIONAL,
    type-dotation-valorisation  TypeDotation       OPTIONAL
}

MsgObjectUpdate ::= SEQUENCE
{
    oid                                 OID,
    pourcentage-construction            INTEGER( 0..100 )  OPTIONAL, 
    pourcentage-valorisation            INTEGER( 0..100 )  OPTIONAL,
    pourcentage-creation-contournement  INTEGER( 0..100 )  OPTIONAL,
    en-preparation                      BOOLEAN            DEFAULT FALSE,
    nb-dotation-construction            INTEGER            OPTIONAL,
    nb-dotation-valorisation            INTEGER            OPTIONAL,   
    localisation                        Localisation       OPTIONAL,
    attributs-specifiques               AttrObjectSpecific OPTIONAL
}

MsgObjectDestruction ::= OID


---------------------------
-- Actions magiques
---------------------------

MagicActionUpdateObject ::= SEQUENCE
{
    pourcentage-construction            INTEGER( 0..100 ) OPTIONAL, 
    pourcentage-valorisation            INTEGER( 0..100 ) OPTIONAL,
    pourcentage-creation-contournement  INTEGER( 0..100 ) OPTIONAL,
    en-preparation                      BOOLEAN           OPTIONAL
}

MagicActionCreateObject ::= SEQUENCE
{
    oid-camp                Camp, 
    type                    EnumObjectType,
    localisation            Localisation,
    nom                     VisibleString      OPTIONAL,    
    attributs-specifiques   AttrObjectSpecific OPTIONAL
}

MagicActionDestroyObjet ::= NULL


MsgObjectMagicAction ::= SEQUENCE
{
    oid-objet             OID,
    action                CHOICE
    {
        create-object   MagicActionCreateObject,
        update-object   MagicActionUpdateObject,
        destroy-object  MagicActionDestroyObjet
    }       
}

MsgObjectMagicActionAck ::= SEQUENCE
{
    oid         OID,
    error-code  EnumObjectErrorCode
}



END -- ScipioObject
