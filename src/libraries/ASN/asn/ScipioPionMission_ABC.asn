--
-- file name : ScipioPionMission_Blinde.asn
--
-- Messages des différentes missions pion blindé
--

ScipioPionMission_ABC DEFINITIONS AUTOMATIC TAGS ::= BEGIN


------------------------------------------
-- Missions ABC
------------------------------------------

Mission-Pion-ABC-ArmerPointDeControle ::= SEQUENCE 
{
    point-de-controle Point
}

Mission-Pion-ABC-OrganiserAccueilColonneRefugies ::= SEQUENCE 
{
    position-installation Point
}

Mission-Pion-ABC-ReconnaitreAxe ::= SEQUENCE 
{
    itineraire      Itineraire
}
Mission-Pion-ABC-Soutenir ::= SEQUENCE
{
    unite-a-soutenir   Agent
}
Mission-Pion-ABC-Couvrir ::= SEQUENCE
{
	position          Point,
    unites-a-couvrir  ListAgent   
}

Mission-Pion-ABC-FlancGarder ::= SEQUENCE
{
    itineraire        Itineraire,
    unites-a-couvrir  ListAgent  
}
Mission-Pion-ABC-Reduire ::= SEQUENCE
{
    unite-a-reduire KnowledgeAgent
}
Mission-Pion-ABC-Appuyer ::= SEQUENCE
{
    unite-a-appuyer  Agent
}
Mission-Pion-ABC-Fixer ::= SEQUENCE
{
    unite-a-fixer	KnowledgeAgent
}
Mission-Pion-ABC-RenseignerSur ::= SEQUENCE
{
    point-a-renseigner  Point
}
Mission-Pion-ABC-ControlerZone ::= SEQUENCE 
{
    zone      Polygon
}
Mission-Pion-ABC-Surveiller ::= SEQUENCE
{
    position  Point
}
Mission-Pion-ABC-Barrer ::= SEQUENCE
{
    position-installation	Point
}
Mission-Pion-ABC-Attaquer ::= SEQUENCE
{
    itineraire-assaut      Itineraire  -- LD obligatoire
}
Mission-Pion-ABC-ReconnaitrePoint ::= SEQUENCE
{
    point-a-reconnaitre       Point
}
Mission-Pion-ABC-Eclairer ::= SEQUENCE
{
    itineraire  Itineraire
}
Mission-Pion-ABC-Jalonner ::= SEQUENCE
{
    itineraire  Itineraire
}
Mission-Pion-ABC-ContreAttaquer ::= SEQUENCE
{
    itineraire-assaut	Itineraire
}
Mission-Pion-ABC-SemparerZone ::= SEQUENCE
{
    zone-a-prendre Polygon
}
Mission-Pion-ABC-ReleverUnite ::= SEQUENCE
{
    unite-a-relever Agent
}
Mission-Pion-ABC-ArmerPIA ::= SEQUENCE
{
    pia	Point
}
Mission-Pion-ABC-OuvrirItineraire ::= SEQUENCE
{
    itineraire       Itineraire
}
Mission-Pion-ABC-RASIT-RenseignerSur ::= SEQUENCE
{
    zone Polygon
}

Mission-Pion-ABC-EscorterUnite ::= SEQUENCE
{
    unite-a-escorter Agent
}

Mission-Pion-ABC-EscorterUnites ::= SEQUENCE
{
    automate-a-escorter Automate
}

Mission-Pion-ABC-AppuyerSurPosition ::= SEQUENCE
{
	position          Point,
    unites-a-appuyer  ListAgent   
}

-- Missions internes
Mission-Pion-ABC-Freiner ::= SEQUENCE
{
    itineraire  Itineraire
}

END -- ScipioPionMission_ABC
