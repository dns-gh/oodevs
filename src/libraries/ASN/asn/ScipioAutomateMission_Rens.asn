--
-- file name : ScipioAutomateMission.asn
--
-- Messages des différentes missions automate Rens
--

ScipioAutomateMission_RENS DEFINITIONS AUTOMATIC TAGS ::= BEGIN

-- ROHUM (RBRR + URH)
Mission-Automate-RENS-ROHUM-RenseignerSur ::= SEQUENCE
{
    zone-a-observer Polygon
}

Mission-Automate-RENS-ROHUM-OrienterGuider ::= SEQUENCE
{
	ami Automate
}

Mission-Automate-RENS-ROHUM-SExfiltrer ::= SEQUENCE
{
    zone-de-regroupement Polygon
}

-- ROIM (Drones + CL289 + SDTI)

Mission-Automate-RENS-ROIM-CL289-RenseignerSur ::= SEQUENCE
{
    ficelle-de-vole      Itineraire,
    zones-de-recherche   ListPolygon    
}

Mission-Automate-RENS-ROIM-SDTI-RenseignerSur ::= SEQUENCE
{
    ficelle-de-vole      Itineraire
}

-- ROEM

Mission-Automate-RENS-ROEM-Appuyer ::= SEQUENCE
{ 
    position-deploiement Point,
    point-regroupement   Point
}

Mission-Automate-RENS-ROEM-RenseignerSur ::= SEQUENCE
{
    zone Polygon
}

-- RADINT (VIVIANE + HORIZON)      

Mission-Automate-RENS-RADINT-RenseignerSur ::= SEQUENCE
{
    zone Polygon
}

END -- ScipioAutomateMission_RENS
