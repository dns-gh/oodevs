--
-- file name : ScipioAutomateMission.asn
--
-- Messages des différentes missions automate NBC
--

ScipioAutomateMission_NBC DEFINITIONS AUTOMATIC TAGS ::= BEGIN

Mission-Automate-NBC-ReconnaitreUnAxe ::= SEQUENCE
{    
}

Mission-Automate-NBC-ReconnaitreUneZone ::= SEQUENCE
{
    zone   Polygon
}       

Mission-Automate-NBC-ArmerUnSiteDeDecontamination ::= SEQUENCE
{
    site   Polygon
}       

Mission-Automate-NBC-DecontaminerUneZone ::= SEQUENCE
{
    zone   Polygon
}

Mission-Automate-NBC-ReconnaitreDesSitesROTA ::= SEQUENCE
{
    sites-ROTA ListKnowledgeObject
}
     
END -- ScipioAutomateMission_NBC
