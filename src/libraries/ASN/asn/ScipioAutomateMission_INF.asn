--
-- file name : ScipioAutomateMission.asn
--
-- Messages des différentes missions automate infanterie
--

ScipioAutomateMission_INF DEFINITIONS AUTOMATIC TAGS ::= BEGIN

IMPORTS EnumObjectType FROM ScipioObject;


------------------------------------------
-- Mission INF
------------------------------------------

Mission-Automate-INF-AttaquerSouplesse ::= SEQUENCE
{
    -- LD obligatoire
    objectifs   ListPoint
}

Mission-Automate-INF-Appuyer  ::= SEQUENCE
{
    compagnie Automate 
}

Mission-Automate-INF-Controler  ::= SEQUENCE
{
    zone                Polygon,
    preparer-terrain    BOOLEAN
}

Mission-Automate-INF-Couvrir  ::= SEQUENCE
{
    compagnie Automate,  
    objectifs ListPoint
}

Mission-Automate-INF-DonnerCoupArret  ::= SEQUENCE 
{
    -- LCAR obligatoire
    zone-regroupement  	Polygon,
    preparer-terrain    BOOLEAN DEFAULT FALSE
}

Mission-Automate-INF-Eclairer ::= SEQUENCE
{
}

Mission-Automate-INF-FlancGarder ::= SEQUENCE
{
    compagnie Automate 
}

Mission-Automate-INF-Freiner ::= SEQUENCE -- Cette mission nécessite une LCAR
{
	-- LCARs obligatoires
}

Mission-Automate-INF-Harceler ::= SEQUENCE
{
    zone-surveillance   Polygon,
    point-regroupement  Polygon
}

Mission-Automate-INF-Interdire ::= SEQUENCE
{
    points-a-interdire  ListPoint,
    preparer-terrain    BOOLEAN DEFAULT FALSE
}

Mission-Automate-INF-MenerDefenseUsure ::= SEQUENCE -- Cette mission nécessite une LCAR
{
}

Mission-Automate-INF-PrendrePreciserMaintenirContact ::= SEQUENCE
{
}

Mission-Automate-INF-ReconnaissanceOffensive ::= SEQUENCE
{
}

Mission-Automate-INF-RecueillirUnite ::= SEQUENCE 
{
    -- LR obligatoire
    zone-deploiement	Polygon,
    compagnie   		Automate, 
    pias        		ListPoint
}

Mission-Automate-INF-Reduire ::= SEQUENCE
{
    points-resistance   ListPoint
}

Mission-Automate-INF-Relever ::= SEQUENCE
{
    compagnie   Automate
}

Mission-Automate-INF-RompreContact ::= SEQUENCE
{
    zone-regroupement Polygon
}

Mission-Automate-INF-Surveiller ::= SEQUENCE
{
    zone               	Polygon,
    zone-regroupement 	Polygon
}

Mission-Automate-INF-Semparer ::= SEQUENCE
{
    objectif    Polygon
}

Mission-Automate-INF-Fixer ::= SEQUENCE
{
    ennemis ListKnowledgeAgent
}

Mission-Automate-INF-AttaquerEnTerrainDifficile::= SEQUENCE
{
    -- LD obligatoire
    objectifs   ListPoint
}

Mission-Automate-INF-BarrerDirection ::= SEQUENCE
{
    position 		    Polygon,
    preparer-terrain    BOOLEAN DEFAULT FALSE
}

Mission-Automate-INF-DefendreFerme ::= SEQUENCE
{
    position 		    Polygon,
    preparer-terrain    BOOLEAN DEFAULT FALSE
}

Mission-Automate-INF-Tenir ::= SEQUENCE
{
    position 		    Polygon,
    preparer-terrain    BOOLEAN DEFAULT FALSE
}

-----------------------------------
-- Nouvelles Missions INF Automate
-----------------------------------

Mission-Automate-INF-AppuyerUnFreinage ::= SEQUENCE
{
	compagnie   Automate
}

Mission-Automate-INF-AppuyerUneAttaque ::= SEQUENCE
{
	compagnie   Automate 
}

Mission-Automate-INF-Soutenir ::= SEQUENCE
{
	compagnie   Automate 
}

Mission-Automate-INF-EscorterUnite ::= SEQUENCE
{
    unite-a-escorter Agent
}

Mission-Automate-INF-EscorterUnites ::= SEQUENCE
{
    automate-a-escorter Automate
}

Mission-Automate-INF-AppuyerSurPosition ::= SEQUENCE
{
    position-installation    Polygon,
    compagnie                Automate
}

END -- ScipioAutomateMission_INF
