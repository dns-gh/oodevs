--
-- file name : ScipioAutomateMission.asn
--
-- Messages des différentes missions automate Rens
--

ScipioAutomateMission_TRANS DEFINITIONS AUTOMATIC TAGS ::= BEGIN

IMPORTS Polygon FROM ScipioBase;

Mission-Automate-TRANS-Commander ::= SEQUENCE
{
    zone-deploiement Polygon
}

END -- ScipioAutomateMission_TRANS
