--
-- file name : ScipioLogRavitaillement.asn
--
-- Messages de gestion de la chaine logistique ravitaillement
--

ScipioLogRavitaillement DEFINITIONS AUTOMATIC TAGS ::= BEGIN

DemandeDotation ::= SEQUENCE
{
    ressource-id        TypeDotation,
    quantite-demandee   INTEGER,
    quantite-accordee   INTEGER,
    quantite-en-transit INTEGER
}

MsgLogRavitaillementTraitementCreation ::= SEQUENCE
{
    oid-consigne    OID,
    oid-automate    Automate,  
    dotations       SEQUENCE OF DemandeDotation
}

EnumLogRavitaillementTraitementEtat ::= ENUMERATED
{ 
    convoi-en-attente-camions                   (0),
    convoi-constitution                         (1),
    convoi-deplacement-vers-point-chargement    (2),
    convoi-chargement                           (3),
    convoi-deplacement-vers-point-dechargement  (4),
    convoi-dechargement                         (5),
    convoi-deplacement-retour                   (6),
    termine                                     (7)
}

MsgLogRavitaillementTraitementUpdate ::= SEQUENCE
{
    oid-consigne                                OID,
    oid-automate                                Automate,                                     -- automate demandeur
    oid-automate-log-traitant                   Automate                            OPTIONAL, -- automate LOG gérant le ravitaillement, 0 si aucun automate
    oid-automate-log-fournissant-moyens-convoi  Automate                            OPTIONAL, -- automate LOG fournissant les moyens de constitution des convois
    oid-pion-convoyant                          Agent                               OPTIONAL, -- pion LOG convoyant le rav
    etat                                        EnumLogRavitaillementTraitementEtat OPTIONAL,
    dotations                                   SEQUENCE OF DemandeDotation         OPTIONAL
}

MsgLogRavitaillementTraitementDestruction ::= SEQUENCE
{
    oid-consigne    OID,
    oid-automate    Automate
}

-- Etat des pions logistiques du ravitaillement
RavitaillementDisponibiliteMoyens ::= SEQUENCE
{
    type-equipement  TypeEquipement,
    nbr-total        INTEGER,
    nbr-disponibles  INTEGER,       
    nbr-au-travail   INTEGER,
    nbr-pretes       INTEGER DEFAULT 0,
    nbr-au-repos     INTEGER OPTIONAL -- applicable uniquement à certains moyens
}

DotationStock ::= SEQUENCE 
{
    ressource-id        TypeDotation,
    quantite-disponible INTEGER
}

MsgLogRavitaillementEtat ::= SEQUENCE
{
    oid-pion                             Agent,    
    chaine-activee                       BOOLEAN                                       OPTIONAL,
    stocks                               SEQUENCE OF DotationStock                     OPTIONAL, -- Seules les dotations qui ont changées sont envoyées
    disponibilites-transporteurs-convois SEQUENCE OF RavitaillementDisponibiliteMoyens OPTIONAL
}


DotationQuota ::= SEQUENCE
{
    ressource-id        TypeDotation,
    quota-disponible    INTEGER
}

MsgLogRavitaillementChangeQuotas ::= SEQUENCE
{
    oid-donneur  Automate,
    oid-receveur Automate,
    quotas       SEQUENCE OF DotationQuota -- Tous les quotas sont envoyés, même ceux dont la valeur n'a pas changé
}
MsgLogRavitaillementChangeQuotasAck ::= ENUMERATED
{
    no-error              (0),
    error-invalid-donneur (1),
    error-invalid-receveur(2)
}

MsgLogRavitaillementPousserFlux ::= SEQUENCE
{
    oid-donneur  Automate,
    oid-receveur Automate,
    stocks       SEQUENCE OF DotationStock
}
MsgLogRavitaillementPousserFluxAck ::= ENUMERATED
{
    no-error              (0),
    error-invalid-donneur (1),
    error-invalid-receveur(2)
}
   
MsgLogRavitaillementQuotas ::= SEQUENCE
{
    oid-automate  Automate,
    quotas        SEQUENCE OF DotationQuota -- Tous est envoyé
}

END -- ScipioLogRavitaillement
