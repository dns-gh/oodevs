--
-- file name : ScipioAutomateOrder.asn
--
-- Messages de gestion des ordres niveau automate
--

ScipioAutomateOrder DEFINITIONS AUTOMATIC TAGS ::= BEGIN

IMPORTS OID, Point, CoordUTM, Localisation FROM ScipioBase
IMPORTS Itineraire, Direction, Segment, ListAgent, ListOID FROM ScipioBase
IMPORTS EnumUnitNatureWeapon,
        EnumUnitNatureSpecialization,
        EnumUnitNatureQualifier,
        EnumUnitNatureCategory,
        EnumUnitNatureMobility FROM ScipioBase
IMPORTS EnumOrderErrorCode FROM ScipioOrder
IMPORTS MsgPionOrder FROM ScipioPionOrder

IMPORTS Mission-Automate-ALAT-Heliporter,
        Mission-Automate-ALAT-Jalonner,
        Mission-Automate-ALAT-Helitransporter,
        Mission-Automate-ALAT-Appuyer,
        Mission-Automate-ALAT-Couvrir,
        Mission-Automate-ALAT-Surveiller,
        Mission-Automate-ALAT-Reconnaitre,
        Mission-Automate-ALAT-Freiner,
        Mission-Automate-ALAT-Escorter,
        Mission-Automate-ALAT-Attaquer,
        Mission-Automate-ALAT-AttaquerFormationAeromobile,
        Mission-Automate-ALAT-RecueillirFormationAeromobile,
        Mission-Automate-ALAT-DetruireNeutraliserDansProfondeur,
        Mission-Automate-ALAT-DetruireNeutraliserDansZone,
        Mission-Automate-ALAT-DonnerCoupArret,
        Mission-Automate-ALAT-AllerSeRecompleter FROM ScipioAutomateMission_ALAT
        
IMPORTS Mission-Automate-ASA-DefendreSite,
        Mission-Automate-ASA-DefendreZone,
        Mission-Automate-ASA-DefendreUnites,
        Mission-Automate-ASA-Surveiller,
        Mission-Automate-ASA-DefendreItineraire,
        Mission-Automate-ASA-MISTRAL-DefendreZone,
        Mission-Automate-ASA-MISTRAL-DefendreSite,
        Mission-Automate-ASA-MISTRAL-Surveiller,        
        Mission-Automate-ASA-HAWK-DefendreZone,
        Mission-Automate-ASA-HAWK-DefendreSite,
        Mission-Automate-ASA-HAWK-Surveiller FROM ScipioAutomateMission_ASA
        
IMPORTS Mission-Automate-ASS-SeDeployer,
        Mission-Automate-ASS-ReconnaitreZonesDeploiement,
        Mission-Automate-ASS-AcquerirObjectifs FROM ScipioAutomateMission_ASS
        
IMPORTS Mission-Automate-ABC-Appuyer,
        Mission-Automate-ABC-Attaquer,
        Mission-Automate-ABC-ContreAttaquer,
        Mission-Automate-ABC-Controler,
        Mission-Automate-ABC-Couvrir,
        Mission-Automate-ABC-DonnerCoupArret,
        Mission-Automate-ABC-Eclairer,
        Mission-Automate-ABC-EffectuerRaid,
        Mission-Automate-ABC-Interdire,
        Mission-Automate-ABC-Jalonner,
        Mission-Automate-ABC-PrendrePreciserContact,
        Mission-Automate-ABC-Reconnaitre,
        Mission-Automate-ABC-ReconnaitrePoint,
        Mission-Automate-ABC-Reduire,
        Mission-Automate-ABC-ReleverEnDepassant,
        Mission-Automate-ABC-Semparer,
        Mission-Automate-ABC-Tenir,
        Mission-Automate-ABC-Soutenir,
        Mission-Automate-ABC-Surveiller,
        Mission-Automate-ABC-FlancGarder,
        Mission-Automate-ABC-RenseignerSur,
        Mission-Automate-ABC-Fixer,
        Mission-Automate-ABC-Freiner,
        Mission-Automate-ABC-SurveillerItineraire,
        Mission-Automate-ABC-RenseignerSurUnAxe,
        Mission-Automate-ABC-RecueillirUnite,
        Mission-Automate-ABC-EscorterUnite,
        Mission-Automate-ABC-EscorterUnites,        
        Mission-Automate-ABC-ArmerPointDeControle, 
        Mission-Automate-ABC-OrganiserAccueilColonneRefugies, 
        Mission-Automate-ABC-ProtegerPC,
        Mission-Automate-ABC-AppuyerSurPosition FROM ScipioAutomateMission_ABC
        
IMPORTS Mission-Automate-GEN-SeDeployer 
        Mission-Automate-GEN-ReconnaitreZone 
        Mission-Automate-GEN-RealiserTravaux 
        Mission-Automate-GEN-OuvrirItineraires 
        Mission-Automate-GEN-RetablirItineraires 
        Mission-Automate-GEN-FaireFranchir 
        Mission-Automate-GEN-FranchirDeViveForce, 
        Mission-Automate-GEN-DegagerObstaclesDansZone FROM ScipioAutomateMission_GEN
        
IMPORTS Mission-Automate-INF-AttaquerSouplesse,
        Mission-Automate-INF-Appuyer,
        Mission-Automate-INF-Controler,
        Mission-Automate-INF-Couvrir,
        Mission-Automate-INF-DonnerCoupArret,
        Mission-Automate-INF-Eclairer,
        Mission-Automate-INF-FlancGarder,
        Mission-Automate-INF-Freiner,
        Mission-Automate-INF-Harceler,
        Mission-Automate-INF-Interdire,
        Mission-Automate-INF-MenerDefenseUsure,
        Mission-Automate-INF-PrendrePreciserMaintenirContact,
        Mission-Automate-INF-ReconnaissanceOffensive,
        Mission-Automate-INF-RecueillirUnite,
        Mission-Automate-INF-Reduire,
        Mission-Automate-INF-Relever,
        Mission-Automate-INF-RompreContact,
        Mission-Automate-INF-Surveiller,
        Mission-Automate-INF-Semparer,
        Mission-Automate-INF-Fixer,
        Mission-Automate-INF-AttaquerEnTerrainDifficile,
        Mission-Automate-INF-BarrerDirection,
        Mission-Automate-INF-DefendreFerme,
        Mission-Automate-INF-Tenir,
        Mission-Automate-INF-AppuyerUnFreinage,
        Mission-Automate-INF-AppuyerUneAttaque,
        Mission-Automate-INF-Soutenir,
        Mission-Automate-INF-EscorterUnite,
        Mission-Automate-INF-EscorterUnites,
        Mission-Automate-INF-AppuyerSurPosition FROM ScipioAutomateMission_INF
        
IMPORTS Mission-Automate-LOG-SeDeployer,
        Mission-Automate-LOG-AppuyerMouvement,
        Mission-Automate-LOG-ReconnaitreItineraire,
        Mission-Automate-LOG-AppuyerMouvementDansZone,
        Mission-Automate-LOG-MettreEnOeuvreZoneStationnement,
        Mission-Automate-LOG-AppuyerFranchissementDansZone,
        Mission-Automate-LOG-BloquerZone,
        Mission-Automate-LOG-ReconnaitreZoneContaminee,
        Mission-Automate-LOG-ReconnaitreZoneDeDeploiement,
        Mission-Automate-LOG-Surveiller,
        Mission-Automate-LOG-ArmerPIAs FROM ScipioAutomateMission_LOG
        
IMPORTS Mission-Automate-Test-MoveTo,
        Mission-Automate-Transporter,
        Mission-Automate-Decrocher,
        Mission-Automate-ReleverSurPlace,
        Mission-Automate-FaireMouvement,
        Mission-Automate-SeFaireDecontaminer,
        Mission-Automate-Franchir,
        Mission-Automate-Stationner,
        Mission-Automate-SeFaireTransporter,
        Mission-Automate-SeRecompleter,
        Mission-Automate-SeRendre,
        Mission-Automate-FaireMouvementVersCampRefugies,
        Mission-Automate-InterdireFranchissementPopulations,
        Mission-Automate-FiltrerPopulations,
        Mission-Automate-CanaliserPopulations,
        Mission-Automate-ControlerPopulationsDansZone,
        Mission-Automate-SecuriserZoneContrePopulations,
        Mission-Automate-ASY-CommettreExactionsSurPopulationDansZone,
        Mission-Automate-Generique FROM ScipioAutomateMission_Misc
        
IMPORTS Mission-Automate-NBC-ReconnaitreUnAxe,
        Mission-Automate-NBC-ReconnaitreUneZone,
        Mission-Automate-NBC-ArmerUnSiteDeDecontamination,
        Mission-Automate-NBC-DecontaminerUneZone,
        Mission-Automate-NBC-ReconnaitreDesSitesROTA FROM ScipioAutomateMission_NBC
        
IMPORTS Mission-Automate-RENS-ROHUM-RenseignerSur,
        Mission-Automate-RENS-ROHUM-OrienterGuider,
        Mission-Automate-RENS-ROHUM-SExfiltrer,
        Mission-Automate-RENS-ROIM-CL289-RenseignerSur,
        Mission-Automate-RENS-ROIM-SDTI-RenseignerSur,
        Mission-Automate-RENS-ROEM-Appuyer,
        Mission-Automate-RENS-ROEM-RenseignerSur,
        Mission-Automate-RENS-RADINT-RenseignerSur FROM ScipioAutomateMission_RENS
       
IMPORTS Mission-Automate-TRANS-Commander FROM ScipioAutomateMission_TRANS;

Mission-Automate ::= CHOICE
{
    mission-automate-alat-aller-se-recompleter                                      Mission-Automate-ALAT-AllerSeRecompleter,
    mission-automate-alat-detruire-neutraliser-dans-profondeur                      Mission-Automate-ALAT-DetruireNeutraliserDansProfondeur,
    mission-automate-alat-detruire-neutraliser-dans-zone                            Mission-Automate-ALAT-DetruireNeutraliserDansZone,    
    mission-automate-alat-donner-coup-arret                                         Mission-Automate-ALAT-DonnerCoupArret,
    mission-automate-alat-attaquer-formation-aeromobile                             Mission-Automate-ALAT-AttaquerFormationAeromobile,
    mission-automate-alat-recueillir-formation-aeromobile                           Mission-Automate-ALAT-RecueillirFormationAeromobile,
    mission-automate-alat-heliporter                                                Mission-Automate-ALAT-Heliporter,
    mission-automate-alat-jalonner                                                  Mission-Automate-ALAT-Jalonner,
    mission-automate-alat-helitransporter                                           Mission-Automate-ALAT-Helitransporter,
    mission-automate-alat-appuyer                                                   Mission-Automate-ALAT-Appuyer,
    mission-automate-alat-couvrir                                                   Mission-Automate-ALAT-Couvrir,
    mission-automate-alat-surveiller                                                Mission-Automate-ALAT-Surveiller,
    mission-automate-alat-reconnaitre                                               Mission-Automate-ALAT-Reconnaitre,
    mission-automate-alat-freiner                                                   Mission-Automate-ALAT-Freiner,
    mission-automate-alat-escorter                                                  Mission-Automate-ALAT-Escorter,
    mission-automate-alat-attaquer                                                  Mission-Automate-ALAT-Attaquer,
    mission-automate-asa-defendre-site                                              Mission-Automate-ASA-DefendreSite,
    mission-automate-asa-defendre-zone                                              Mission-Automate-ASA-DefendreZone,
    mission-automate-asa-defendre-unites                                            Mission-Automate-ASA-DefendreUnites,
    mission-automate-asa-surveiller                                                 Mission-Automate-ASA-Surveiller,    
    mission-automate-asa-defendre-itineraire                                        Mission-Automate-ASA-DefendreItineraire,
    mission-automate-asa-mistral-defendre-zone                                      Mission-Automate-ASA-MISTRAL-DefendreZone,
    mission-automate-asa-mistral-defendre-site                                      Mission-Automate-ASA-MISTRAL-DefendreSite,
    mission-automate-asa-mistral-surveiller                                         Mission-Automate-ASA-MISTRAL-Surveiller,
    mission-automate-asa-hawk-defendre-zone                                         Mission-Automate-ASA-HAWK-DefendreZone,
    mission-automate-asa-hawk-defendre-site                                         Mission-Automate-ASA-HAWK-DefendreSite,
    mission-automate-asa-hawk-surveiller                                            Mission-Automate-ASA-HAWK-Surveiller,             
    mission-automate-ass-se-deployer                                                Mission-Automate-ASS-SeDeployer,
    mission-automate-ass-reconnaitre-zones-deploiement                              Mission-Automate-ASS-ReconnaitreZonesDeploiement,
    mission-automate-ass-acquerir-objectifs                                         Mission-Automate-ASS-AcquerirObjectifs,
    mission-automate-abc-appuyer                                                    Mission-Automate-ABC-Appuyer,
    mission-automate-abc-attaquer                                                   Mission-Automate-ABC-Attaquer,
    mission-automate-abc-contre-attaquer                                            Mission-Automate-ABC-ContreAttaquer,
    mission-automate-abc-controler                                                  Mission-Automate-ABC-Controler,
    mission-automate-abc-couvrir                                                    Mission-Automate-ABC-Couvrir,
    mission-automate-abc-donner-coup-arret                                          Mission-Automate-ABC-DonnerCoupArret,
    mission-automate-abc-eclairer                                                   Mission-Automate-ABC-Eclairer,
    mission-automate-abc-effectuer-raid                                             Mission-Automate-ABC-EffectuerRaid,
    mission-automate-abc-interdire                                                  Mission-Automate-ABC-Interdire,
    mission-automate-abc-jalonner                                                   Mission-Automate-ABC-Jalonner,
    mission-automate-abc-prendre-preciser-contact                                   Mission-Automate-ABC-PrendrePreciserContact,
    mission-automate-abc-reconnaitre                                                Mission-Automate-ABC-Reconnaitre,
    mission-automate-abc-reconnaitre-point                                          Mission-Automate-ABC-ReconnaitrePoint,
    mission-automate-abc-reduire                                                    Mission-Automate-ABC-Reduire,
    mission-automate-abc-relever-en-depassant                                       Mission-Automate-ABC-ReleverEnDepassant,
    mission-automate-abc-semparer                                                   Mission-Automate-ABC-Semparer,
    mission-automate-abc-tenir                                                      Mission-Automate-ABC-Tenir,
    mission-automate-abc-soutenir                                                   Mission-Automate-ABC-Soutenir,
    mission-automate-abc-surveiller                                                 Mission-Automate-ABC-Surveiller,
    mission-automate-abc-flanc-garder                                               Mission-Automate-ABC-FlancGarder,
    mission-automate-abc-renseigner-sur                                             Mission-Automate-ABC-RenseignerSur,
    mission-automate-abc-fixer                                                      Mission-Automate-ABC-Fixer,
    mission-automate-abc-freiner                                                    Mission-Automate-ABC-Freiner,
    mission-automate-abc-surveiller-itineraire                                      Mission-Automate-ABC-SurveillerItineraire,
    mission-automate-abc-renseigner-sur-un-axe                                      Mission-Automate-ABC-RenseignerSurUnAxe,
    mission-automate-abc-recueillir-unite                                           Mission-Automate-ABC-RecueillirUnite,
    mission-automate-abc-escorter-unite                                             Mission-Automate-ABC-EscorterUnite,    
    mission-automate-abc-escorter-unites                                            Mission-Automate-ABC-EscorterUnites,
    mission-automate-abc-armer-point-de-controle                                    Mission-Automate-ABC-ArmerPointDeControle,
    mission-automate-abc-organiser-accueil-colonne-refugies                         Mission-Automate-ABC-OrganiserAccueilColonneRefugies, 
    mission-automate-abc-proteger-pc                                                Mission-Automate-ABC-ProtegerPC,    
    mission-automate-abc-appuyer-sur-position                                       Mission-Automate-ABC-AppuyerSurPosition,
    mission-automate-gen-se-deployer                                                Mission-Automate-GEN-SeDeployer,
    mission-automate-gen-reconnaitre-zone                                           Mission-Automate-GEN-ReconnaitreZone,
    mission-automate-gen-realiser-travaux                                           Mission-Automate-GEN-RealiserTravaux,
    mission-automate-gen-ouvrir-itineraires                                         Mission-Automate-GEN-OuvrirItineraires,
    mission-automate-gen-retablir-itineraires                                       Mission-Automate-GEN-RetablirItineraires,
    mission-automate-gen-faire-franchir                                             Mission-Automate-GEN-FaireFranchir,
    mission-automate-gen-franchir-de-vive-force                                     Mission-Automate-GEN-FranchirDeViveForce,
    mission-automate-gen-degager-obstacles-dans-zone                                Mission-Automate-GEN-DegagerObstaclesDansZone,
    mission-automate-inf-attaquer-souplesse                                         Mission-Automate-INF-AttaquerSouplesse,
    mission-automate-inf-appuyer                                                    Mission-Automate-INF-Appuyer,
    mission-automate-inf-controler                                                  Mission-Automate-INF-Controler,
    mission-automate-inf-couvrir                                                    Mission-Automate-INF-Couvrir,
    mission-automate-inf-donner-coup-arret                                          Mission-Automate-INF-DonnerCoupArret,
    mission-automate-inf-eclairer                                                   Mission-Automate-INF-Eclairer,
    mission-automate-inf-flanc-garder                                               Mission-Automate-INF-FlancGarder,
    mission-automate-inf-freiner                                                    Mission-Automate-INF-Freiner,
    mission-automate-inf-harceler                                                   Mission-Automate-INF-Harceler,
    mission-automate-inf-interdire                                                  Mission-Automate-INF-Interdire,
    mission-automate-inf-mener-defense-usure                                        Mission-Automate-INF-MenerDefenseUsure,
    mission-automate-inf-prendre-preciser-maintenir-contact                         Mission-Automate-INF-PrendrePreciserMaintenirContact,
    mission-automate-inf-reconnaissance-offensive                                   Mission-Automate-INF-ReconnaissanceOffensive,
    mission-automate-inf-recueillir-unite                                           Mission-Automate-INF-RecueillirUnite,
    mission-automate-inf-reduire                                                    Mission-Automate-INF-Reduire,
    mission-automate-inf-relever                                                    Mission-Automate-INF-Relever,
    mission-automate-inf-rompre-contact                                             Mission-Automate-INF-RompreContact,
    mission-automate-inf-surveiller                                                 Mission-Automate-INF-Surveiller,
    mission-automate-inf-semparer                                                   Mission-Automate-INF-Semparer,
    mission-automate-inf-fixer                                                      Mission-Automate-INF-Fixer,
    mission-automate-inf-attaquer-en-terrain-difficile                              Mission-Automate-INF-AttaquerEnTerrainDifficile,
    mission-automate-inf-barrer-direction                                           Mission-Automate-INF-BarrerDirection,
    mission-automate-inf-defendre-ferme                                             Mission-Automate-INF-DefendreFerme,
    mission-automate-inf-tenir                                                      Mission-Automate-INF-Tenir,
    mission-automate-inf-appuyer-un-freinage                                        Mission-Automate-INF-AppuyerUnFreinage,
    mission-automate-inf-appuyer-une-attaque                                        Mission-Automate-INF-AppuyerUneAttaque,
    mission-automate-inf-soutenir                                                   Mission-Automate-INF-Soutenir,
    mission-automate-inf-escorter-unite                                             Mission-Automate-INF-EscorterUnite,    
    mission-automate-inf-escorter-unites                                            Mission-Automate-INF-EscorterUnites,
    mission-automate-inf-appuyer-sur-position                                       Mission-Automate-INF-AppuyerSurPosition,    
    mission-automate-log-se-deployer                                                Mission-Automate-LOG-SeDeployer,
    mission-automate-log-appuyer-mouvement                                          Mission-Automate-LOG-AppuyerMouvement,
    mission-automate-log-reconnaitre-itineraire                                     Mission-Automate-LOG-ReconnaitreItineraire,
    mission-automate-log-appuyer-mouvement-dans-zone                                Mission-Automate-LOG-AppuyerMouvementDansZone,
    mission-automate-log-mettre-en-oeuvre-zone-stationnement                        Mission-Automate-LOG-MettreEnOeuvreZoneStationnement,
    mission-automate-log-appuyer-franchissement-dans-zone                           Mission-Automate-LOG-AppuyerFranchissementDansZone,
    mission-automate-log-bloquer-zone                                               Mission-Automate-LOG-BloquerZone,
    mission-automate-log-reconnaitre-zone-contaminee                                Mission-Automate-LOG-ReconnaitreZoneContaminee,
    mission-automate-log-reconnaitre-zone-de-deploiement                            Mission-Automate-LOG-ReconnaitreZoneDeDeploiement,
    mission-automate-log-surveiller                                                 Mission-Automate-LOG-Surveiller,        
    mission-automate-log-armer-pias                                                 Mission-Automate-LOG-ArmerPIAs,
    mission-automate-test-move-to                                                   Mission-Automate-Test-MoveTo,
    mission-automate-decrocher                                                      Mission-Automate-Decrocher,
    mission-automate-relever-sur-place                                              Mission-Automate-ReleverSurPlace,
    mission-automate-faire-mouvement                                                Mission-Automate-FaireMouvement,
    mission-automate-se-faire-decontaminer                                          Mission-Automate-SeFaireDecontaminer,
    mission-automate-franchir                                                       Mission-Automate-Franchir,
    mission-automate-stationner                                                     Mission-Automate-Stationner,
    mission-automate-se-faire-transporter                                           Mission-Automate-SeFaireTransporter,
    mission-automate-transporter                                                    Mission-Automate-Transporter,    
    mission-automate-se-recompleter                                                 Mission-Automate-SeRecompleter,
    mission-automate-se-rendre                                                      Mission-Automate-SeRendre,
    mission-automate-faire-mouvement-vers-camp-refugies                             Mission-Automate-FaireMouvementVersCampRefugies,
    mission-automate-interdire-franchissement-populations                           Mission-Automate-InterdireFranchissementPopulations,
    mission-automate-filtrer-populations                                            Mission-Automate-FiltrerPopulations,
    mission-automate-canaliser-populations                                          Mission-Automate-CanaliserPopulations,
    mission-automate-controler-populations-dans-zone                                Mission-Automate-ControlerPopulationsDansZone,
    mission-automate-securiser-zone-contre-populations                              Mission-Automate-SecuriserZoneContrePopulations,
    mission-automate-asy-commettre-exactions-sur-population-dans-zone               Mission-Automate-ASY-CommettreExactionsSurPopulationDansZone,
    mission-automate-generique                                                      Mission-Automate-Generique,    
    mission-automate-nbc-reconnaitre-un-axe                                         Mission-Automate-NBC-ReconnaitreUnAxe,
    mission-automate-nbc-reconnaitre-une-zone                                       Mission-Automate-NBC-ReconnaitreUneZone,
    mission-automate-nbc-armer-un-site-de-decontamination                           Mission-Automate-NBC-ArmerUnSiteDeDecontamination,
    mission-automate-nbc-decontaminer-une-zone                                      Mission-Automate-NBC-DecontaminerUneZone,
    mission-automate-nbc-reconnaitre-des-sites-rota                                 Mission-Automate-NBC-ReconnaitreDesSitesROTA,
    mission-automate-rens-rohum-renseigner-sur                                      Mission-Automate-RENS-ROHUM-RenseignerSur,
    mission-automate-rens-rohum-orienter-guider                                     Mission-Automate-RENS-ROHUM-OrienterGuider,
    mission-automate-rens-rohum-sexfiltrer                                          Mission-Automate-RENS-ROHUM-SExfiltrer,
    mission-automate-rens-roim-cl289-renseigner-sur                                 Mission-Automate-RENS-ROIM-CL289-RenseignerSur,
    mission-automate-rens-roim-sdti-renseigner-sur                                  Mission-Automate-RENS-ROIM-SDTI-RenseignerSur,       
    mission-automate-rens-roem-appuyer                                              Mission-Automate-RENS-ROEM-Appuyer,
    mission-automate-rens-roem-renseignersur                                        Mission-Automate-RENS-ROEM-RenseignerSur,
    mission-automate-rens-radint-renseignersur                                      Mission-Automate-RENS-RADINT-RenseignerSur,            
    mission-automate-trans-commander                                                Mission-Automate-TRANS-Commander
}

EnumAutomateOrderFormation ::= ENUMERATED
{
    un-echelon      (0),
    deux-echelons   (1)
}

MsgAutomateOrder ::= SEQUENCE
{
    oid-unite-executante    Agent,
    order-context           OrderContext,
    formation               EnumAutomateOrderFormation DEFAULT deux-echelons,
    mission                 Mission-Automate
}

MsgAutomateOrderAck ::= SEQUENCE
{
    oid-unite-executante    Agent,
    error-code		    EnumOrderErrorCode
}

MsgAutomateOrderManagement ::= SEQUENCE
{
    oid-unite-executante    Automate,
    etat                    EnumOrderState
}

MsgAutomateMRT ::= SEQUENCE
{
    automate-id     Agent,
    missions        SEQUENCE OF MsgPionOrder
}

END -- ScipioOrder
