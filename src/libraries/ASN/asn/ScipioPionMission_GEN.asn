--
-- file name : ScipioPionMission_Genie.asn
--
-- Messages des différentes missions pion génie
--

ScipioPionMission_GEN DEFINITIONS AUTOMATIC TAGS ::= BEGIN

EnumGenTypePontage ::= ENUMERATED
{
    continu     (0),
    discontinu  (1)
}

Mission-Pion-GEN-OuvrirItineraire ::= SEQUENCE
{
    itineraire Itineraire
}
Mission-Pion-GEN-RetablirItineraire ::= SEQUENCE
{
    itineraire Itineraire
}

Mission-Pion-GEN-ReconnaitreItineraire ::= SEQUENCE
{                               
    itineraire Itineraire
}
Mission-Pion-GEN-ReconnaitreZone ::= SEQUENCE
{
    zone Localisation
}
Mission-Pion-GEN-ReconnaitreSiteFranchissement ::= SEQUENCE
{
    site-franchissement KnowledgeObject
}
Mission-Pion-GEN-EquiperExploiterSiteFranchissement ::= SEQUENCE
{
    site-franchissement KnowledgeObject,
    point-regroupement  Point,
    type-pontage        EnumGenTypePontage
}

Mission-Pion-GEN-ExecuterVariantement ::= SEQUENCE
{                               
    site-franchissement  KnowledgeObject,
    point-regroupement   Point,
    type-pontage         EnumGenTypePontage
}
Mission-Pion-GEN-DegagerObstacles ::= SEQUENCE
{
    obstacles ListKnowledgeObject
}
Mission-Pion-GEN-ContournerObstacles ::= SEQUENCE
{
    obstacles ListKnowledgeObject
}
Mission-Pion-GEN-DepolluerZone ::= SEQUENCE
{
    zone Localisation
}
Mission-Pion-GEN-Renforcer ::= SEQUENCE
{
    lieu-renforcement   Point,
    unite               Agent
}
Mission-Pion-GEN-RealiserTravauxProtection ::= SEQUENCE
{
    travaux ListMissionGenObject -- postes de tir, travaux de protection
}
Mission-Pion-GEN-RealiserTravauxContreMobilite ::= SEQUENCE
{
    travaux ListMissionGenObject -- obstacles
}
Mission-Pion-GEN-RealiserTravauxAppuiDeploiement ::= SEQUENCE
{
    travaux ListMissionGenObject -- 
}
Mission-Pion-GEN-RealiserCamps ::= SEQUENCE
{
    travaux ListMissionGenObject -- 
}
Mission-Pion-GEN-ReprendreTravaux ::= SEQUENCE
{
    travaux KnowledgeObject
}
Mission-Pion-GEN-AmeliorerMobilite ::= SEQUENCE
{
    zone Polygon
}
Mission-Pion-GEN-ActiverObstacle ::= SEQUENCE
{
    obstacle KnowledgeObject
}

END -- ScipioPionMission_GEN
