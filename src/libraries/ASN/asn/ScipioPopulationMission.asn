--
-- file name : ScipioPopulationMission.asn
--
-- Messages des différentes missions automate blindé
--

ScipioPopulationMission DEFINITIONS AUTOMATIC TAGS ::= BEGIN

IMPORTS Point FROM ScipioBase;

Mission-Population-FaireMouvement ::= SEQUENCE
{
    destination Point
}

Mission-Population-Manifester  ::= SEQUENCE
{
    destination Point
}

Mission-Population-CommettreExactions ::= SEQUENCE
{
    zone Polygon
}

END -- ScipioPopulationMission
