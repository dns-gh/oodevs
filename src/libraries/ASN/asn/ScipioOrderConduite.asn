--
-- file name : ScipioOrderConduite.asn
--
--

ScipioOrderConduite DEFINITIONS AUTOMATIC TAGS ::= BEGIN

IMPORTS OID, CoordUTM, GDH, Agent, KnowledgeObject FROM ScipioBase
IMPORTS Itineraire, Point, Direction, Segment, TypeEquipement, ListAgent FROM ScipioBase
IMPORTS EnumOrderErrorCode                                FROM ScipioOrder
IMPORTS MissionGenObject                                  FROM ScipioAutomateMission_GEN
IMPORTS MaintenancePriorites                              FROM ScipioLogMaintenance
IMPORTS SantePriorites                                    FROM ScipioLogSante
IMPORTS EnumRoe, EnumRoePopulation                        FROM ScipioUnit
IMPORTS EnumLogMaintenanceRegimeTravail                   FROM ScipioLogMaintenance
IMPORTS EnumPopulationAttitude                            FROM ScipioPopulation
IMPORTS Enum_ALAT_PorteeAction, Enum_ALAT_AmbianceMission FROM ScipioPionMission_ALAT;

EnumAmbianceMission ::= ENUMERATED
{
    surete  (0),
    vitesse (1)
}

----------------------------------------------------------------------------
-- Ordres de conduite pions/automates
----------------------------------------------------------------------------
OrderConduite-MettreTenueNBC                        ::= NULL                 -- Dispo même sans mission
OrderConduite-EnleverTenueNBC                       ::= NULL                 -- Dispo même sans mission
OrderConduite-PasserEnSilenceRadio                  ::= NULL                 -- Dispo même sans mission
OrderConduite-ArreterSilenceRadio                   ::= NULL                 -- Dispo même sans mission
OrderConduite-ChangerReglesEngagement               ::= EnumRoe              -- Dispo même sans mission
OrderConduite-ChangerReglesEngagementPopulation     ::= EnumRoePopulation    -- Dispo même sans mission
OrderConduite-PasserEnSilenceRadar                  ::= NULL                 -- Dispo même sans mission
OrderConduite-ArreterSilenceRadar                   ::= NULL                 -- Dispo même sans mission
OrderConduite-RecupererTransporteurs                ::= NULL                 -- Dispo même sans mission, Infanterie : récupération des VABs

OrderConduite-AttendreSePoster                      ::= NULL                  -- Dispo pour toutes les missions
OrderConduite-Poursuivre                            ::= NULL                  -- Dispo pour toutes les missions
OrderConduite-Interrompre                           ::= NULL                  -- Dispo pour toutes les missions
OrderConduite-ChangerAmbiance                       ::= EnumAmbianceMission

OrderConduite-Deboucher                             ::= NULL 
OrderConduite-Decrocher                             ::= NULL
OrderConduite-ModifierRegimeTravailMaintenance      ::= EnumLogMaintenanceRegimeTravail
OrderConduite-ModifierPrioritesReparations          ::= MaintenancePriorites
OrderConduite-ModifierPrioritesBlesses              ::= SantePriorites
OrderConduite-ModifierPrioritesTactiquesReparations ::= ListAutomate
OrderConduite-ModifierPrioritesTactiquesBlesses     ::= ListAutomate
OrderConduite-AcquerirObjectif                      ::= Localisation
OrderConduite-Brouiller                             ::= NULL
OrderConduite-ChangerPositionDebarquement           ::= Point    

OrderConduite-ChangerParametresRecompletementALAT   ::= SEQUENCE
{
    portee_Action       Enum_ALAT_PorteeAction, 
    ambiance_Mission    Enum_ALAT_AmbianceMission
}

---------------------------------------
-- Ordres de conduite pion                                         
---------------------------------------
OrderConduite-Pion-Contourner                       ::= NULL
OrderConduite-Pion-ActiverObstacle                  ::= NULL
OrderConduite-Pion-ExecuterTir                      ::= NULL
OrderConduite-Pion-Emettre                          ::= NULL
OrderConduite-Pion-StopperEmission			        ::= NULL
OrderConduite-Pion-EnvoyerVehicule                  ::= NULL
OrderConduite-Pion-ChangerDePosition                ::= Point

---------------------------------------
-- Ordres de conduite population
---------------------------------------
OrderConduite-Population-ChangerAttitude            ::= EnumPopulationAttitude
  
OrderConduite-Pion-AppliquerFeux ::= SEQUENCE
{
    munitions   TypeDotationTrancheD,
    nb_IT		INTEGER,
    cible       Point 
}

OrderConduite-Pion-RenforcerEnVSRAM                 ::= SEQUENCE
{
    pion-a-renforcer Agent,   -- TC2
    nbr-ambulances   INTEGER 
}
OrderConduite-Pion-TransfererVSRAM                  ::= SEQUENCE
{
    pion-renforce    Agent,  -- TC2 dont on veut extraire les moyens
    pion-a-renforcer Agent,  -- TC2
    nbr-ambulances   INTEGER 
}
OrderConduite-Pion-ReprendreAuxOrdresVSRAM ::= SEQUENCE
{
    pion-renforce  Agent,  -- TC2 dont on veut extraire les moyens
    nbr-ambulances INTEGER -- Le nombre d'ambulances que l'on reprend aux ordres
}

OrderConduite-Pion-RenforcerEnRemorqueurs ::= SEQUENCE
{
    pion-a-renforcer Agent,   -- 
    nbr-remorqueurs  INTEGER 
}
OrderConduite-Pion-TransfererRemorqueurs ::= SEQUENCE
{
    pion-renforce    Agent,  -- pion dont on veut extraire les moyens
    pion-a-renforcer Agent,  -- pion destinataire
    nbr-remorqueurs  INTEGER 
}
OrderConduite-Pion-ReprendreAuxOrdresRemorqueurs ::= SEQUENCE
{
    pion-renforce  Agent,   -- pion dont on veut extraire les moyens
    nbr-remorqueurs INTEGER -- Le nombre de remorqueurs que l'on reprend aux ordres
}

---------------------------------------
-- Ordres de conduite automate
---------------------------------------

EnumTC2GererMaterielAvantDeplacement ::= ENUMERATED
{
    deborder-materiels-vers-bld      (0),
    detruire-materiels-en-reparation (1),
    reparer-materiels-sur-place      (2)
} 

OrderConduite-Automate-TC2-GererMaterielAvantDeplacement ::= EnumTC2GererMaterielAvantDeplacement

OrderConduite-Automate-ReconnaitreZoneImplantation ::= Point 

OrderConduite-Automate-RealiserVariantement ::= SEQUENCE
{
    site-franchissement-original    KnowledgeObject,
    site-franchissement-variante    KnowledgeObject
}
OrderConduite-Automate-DesequiperSiteFranchissement ::= SEQUENCE
{
    site-franchissement KnowledgeObject
}

OrderConduite-Automate-ActiverObstacle ::= KnowledgeObject

OrderConduite-Automate-AffecterPionAObstacle ::= SEQUENCE
{
    pion     Agent,
    obstacle MissionGenObject
}

OrderConduite-Automate-TransfererRenforts ::= SEQUENCE
{
    pion-a-transferer    Agent,
    automate-a-renforcer Automate   
}
                  
----------------------------------------------------------------------------
-- Msg MOS -> SIM
----------------------------------------------------------------------------
MsgOrderConduite ::= SEQUENCE
{
    unit-id         OID,
    order-conduite  CHOICE
    {
        order-conduite-mettre-tenue-nbc                                 OrderConduite-MettreTenueNBC,
        order-conduite-enlever-tenue-nbc                                OrderConduite-EnleverTenueNBC,
        order-conduite-passer-en-silence-radio                          OrderConduite-PasserEnSilenceRadio,
        order-conduite-arreter-silence-radio                            OrderConduite-ArreterSilenceRadio,
        order-conduite-passer-en-silence-radar                          OrderConduite-PasserEnSilenceRadar,
        order-conduite-arreter-silence-radar                            OrderConduite-ArreterSilenceRadar,        
        order-conduite-recuperer-transporteurs                          OrderConduite-RecupererTransporteurs,        
        order-conduite-attendre-se-poster                               OrderConduite-AttendreSePoster,
        order-conduite-poursuivre                                       OrderConduite-Poursuivre,
        order-conduite-interrompre                                      OrderConduite-Interrompre,        
        order-conduite-changer-ambiance                                 OrderConduite-ChangerAmbiance,
        order-conduite-changer-regles-engagement                        OrderConduite-ChangerReglesEngagement,
        order-conduite-changer-parametres-recompletement-alat           OrderConduite-ChangerParametresRecompletementALAT,
        order-conduite-changer-regles-engagement-population             OrderConduite-ChangerReglesEngagementPopulation,        
        order-conduite-deboucher                                        OrderConduite-Deboucher,
        order-conduite-decrocher                                        OrderConduite-Decrocher,                                                               
        order-conduite-acquerir-objectif                                OrderConduite-AcquerirObjectif,
        order-conduite-brouiller                                        OrderConduite-Brouiller,        
        order-conduite-changer-position-debarquement                    OrderConduite-ChangerPositionDebarquement,
        order-conduite-pion-changer-de-position                         OrderConduite-Pion-ChangerDePosition,
        order-conduite-pion-contourner                                  OrderConduite-Pion-Contourner,
		order-conduite-pion-envoyer-vehicule				            OrderConduite-Pion-EnvoyerVehicule, 
        order-conduite-pion-activer-obstacle                            OrderConduite-Pion-ActiverObstacle,
        order-conduite-pion-appliquer-feux                              OrderConduite-Pion-AppliquerFeux,
        order-conduite-pion-executer-tir					            OrderConduite-Pion-ExecuterTir,
        order-conduite-pion-emettre                                     OrderConduite-Pion-Emettre,         
        order-conduite-pion-stopper-emission                            OrderConduite-Pion-StopperEmission, 
        order-conduite-pion-renforcer-en-vs-ram                         OrderConduite-Pion-RenforcerEnVSRAM,
        order-conduite-pion-transferer-vs-ram                           OrderConduite-Pion-TransfererVSRAM,
        order-conduite-pion-reprendre-aux-ordres-vs-ram                 OrderConduite-Pion-ReprendreAuxOrdresVSRAM,        
        order-conduite-pion-renforcer-en-remorqueurs                    OrderConduite-Pion-RenforcerEnRemorqueurs,
        order-conduite-pion-transferer-remorqueurs                      OrderConduite-Pion-TransfererRemorqueurs,
        order-conduite-pion-reprendre-aux-ordres-remorqueurs            OrderConduite-Pion-ReprendreAuxOrdresRemorqueurs,        
        order-conduite-modifier-regime-travail-maintenance              OrderConduite-ModifierRegimeTravailMaintenance,
        order-conduite-modifier-priorites-reparations                   OrderConduite-ModifierPrioritesReparations,
        order-conduite-modifier-priorites-blesses                       OrderConduite-ModifierPrioritesBlesses,
        order-conduite-modifier-priorites-tactiques-reparations         OrderConduite-ModifierPrioritesTactiquesReparations,
        order-conduite-modifier-priorites-tactiques-blesses             OrderConduite-ModifierPrioritesTactiquesBlesses,
        order-conduite-automate-realiser-variantement                   OrderConduite-Automate-RealiserVariantement,
        order-conduite-automate-desequiper-site-franchissement          OrderConduite-Automate-DesequiperSiteFranchissement,
        order-conduite-automate-affecter-pion-a-obstacle                OrderConduite-Automate-AffecterPionAObstacle,
        order-conduite-automate-reconnaitre-zone-implantation           OrderConduite-Automate-ReconnaitreZoneImplantation,
        order-conduite-automate-tc2-gerer-materiel-avant-deplacement    OrderConduite-Automate-TC2-GererMaterielAvantDeplacement,
        order-conduite-automate-activer-obstacle                        OrderConduite-Automate-ActiverObstacle,
        order-conduite-automate-transferer-renforts                     OrderConduite-Automate-TransfererRenforts,
        order-conduite-population-changer-attitude						OrderConduite-Population-ChangerAttitude
    }
}

MsgOrderConduiteAck ::= SEQUENCE
{
    unit-id    OID,
    error-code EnumOrderErrorCode
}

END -- ScipioOrderConduite
