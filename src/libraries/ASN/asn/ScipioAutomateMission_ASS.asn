--
-- file name : ScipioAutomateMission.asn
--
-- Messages des différentes missions automate 3D
--

ScipioAutomateMission_ASS DEFINITIONS AUTOMATIC TAGS ::= BEGIN

IMPORTS NatureAtlas, ListAgent, Agent, Direction, OID, CoordUTM, Point, Itineraire, EnumUnitIdentificationLevel, Segment, GDH, Localisation FROM ScipioBase
IMPORTS EnumModeTir FROM ScipioOrder;

------------------------------------------
-- ASS
------------------------------------------
Mission-Automate-ASS-SeDeployer ::= SEQUENCE  -- mission avant mise en oeuvre, équivalent au deploiement du TC2, idem pour le DLO
{
    zone-deploiement Polygon
}

Mission-Automate-ASS-ReconnaitreZonesDeploiement ::= SEQUENCE
{
	positions-a-reconnaitre ListPoint
}

Mission-Automate-ASS-AcquerirObjectifs ::= SEQUENCE  -- pour Section RATAC
{
    zones-a-observer	  ListPolygon,
    positions-deploiement ListPoint,
	categories      	  NatureAtlas  
}

END -- ScipioAutomateMission_ASS
