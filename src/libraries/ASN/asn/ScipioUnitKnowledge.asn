--
-- file name : ScipioUnitKnowledge.asn
--
-- Messages de gestion de la connaissance d'une unité
--

ScipioUnitKnowledge DEFINITIONS AUTOMATIC TAGS ::= BEGIN

MsgUnitKnowledgeCreation ::= SEQUENCE
{
    oid-connaissance        KnowledgeAgent,   -- id de la connaissance
    oid-groupe-possesseur   KnowledgeGroup,   -- id du groupe de connaissance qui possède cette connaissance
    oid-unite-reelle        Agent            -- id de l'unité réélle pointée par la connaissance
}

AutomatePerception ::= SEQUENCE
{
    oid-compagnie           Automate,
    identification-level    EnumUnitIdentificationLevel
}

MsgUnitKnowledgeUpdate ::= SEQUENCE
{
    oid-connaissance            KnowledgeAgent,
    oid-groupe-possesseur       KnowledgeGroup,

    pertinence                  Pourcentage                    OPTIONAL,
    identification-level        EnumUnitIdentificationLevel    OPTIONAL,
    max-identification-level    EnumUnitIdentificationLevel    OPTIONAL,
    etat-op                     PourcentageLibre               OPTIONAL,
    mort                        BOOLEAN                        OPTIONAL,
    position                    CoordUTM                       OPTIONAL,
    direction                   Direction                      OPTIONAL,
    speed                       Vitesse                        OPTIONAL,
    camp                        OID                            OPTIONAL,
    nature-arme                 EnumUnitNatureWeapon           OPTIONAL,
    nature-niveau               EnumNatureLevel                OPTIONAL,
    nature-pc                   BOOLEAN                        OPTIONAL,
    nature-specialisation       EnumUnitNatureSpecialization   OPTIONAL,
    nature-qualification        EnumUnitNatureQualifier        OPTIONAL,
    nature-categorie            EnumUnitNatureCategory         OPTIONAL,
    nature-mobilite             EnumUnitNatureMobility         OPTIONAL,
    capacite-mission            EnumUnitCapaciteMission        OPTIONAL,
    perception-par-compagnie    SEQUENCE OF AutomatePerception OPTIONAL,
    rendu                       BOOLEAN                        OPTIONAL,
    prisonnier                  BOOLEAN                        OPTIONAL,
    refugie-pris-en-compte      BOOLEAN                        OPTIONAL
}

MsgUnitKnowledgeDestruction ::= SEQUENCE
{
    oid-connaissance        KnowledgeAgent,
    oid-groupe-possesseur   KnowledgeGroup
}

END -- ScipioUnitKnowledge
