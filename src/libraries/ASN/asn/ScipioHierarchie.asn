--
-- file name : ScipioHierarchie.asn
--
-- Messages des changements de hierarchies
--

ScipioHierarchie DEFINITIONS AUTOMATIC TAGS ::= BEGIN

IMPORTS OID FROM ScipioBase;

EnumDiplomatie ::= ENUMERATED
{
    inconnu (0),
    ami     (1),
    ennemi  (2),
    neutre  (3)
}

MsgChangeDiplomatie ::= SEQUENCE
{
    oid-camp1  Camp,
    oid-camp2  Camp,
    diplomatie EnumDiplomatie 
}

EnumChangeDiplomatieErrorCode ::= ENUMERATED
{
    no-error            (0),
    error-invalid-camp  (1)
}

MsgChangeDiplomatieAck ::= SEQUENCE
{
    oid-camp1  Camp,
    oid-camp2  Camp,
    diplomatie EnumDiplomatie,
    error-code EnumChangeDiplomatieErrorCode
}

--
MsgChangeGroupeConnaissance ::= SEQUENCE
{
    oid-automate             Automate,
    oid-camp                 Camp,
    oid-groupe-connaissance  OID 
}

EnumChangeGroupeConnaissanceErrorCode ::= ENUMERATED
{
    no-error                         (0),
    error-invalid-automate           (1),
    error-invalid-camp               (2),
    error-invalid-groupe-connaissance(3)
}

MsgChangeGroupeConnaissanceAck ::= SEQUENCE
{
    oid-automate             Automate,
    oid-camp                 Camp,
    oid-groupe-connaissance  OID,
    error-code               EnumChangeGroupeConnaissanceErrorCode
}

MsgChangeLiensLogistiques ::= SEQUENCE
{
    oid-automate       Automate,
    oid-tc2            Automate OPTIONAL,
    oid-maintenance    Automate OPTIONAL,
    oid-sante          Automate OPTIONAL,
    oid-ravitaillement Automate OPTIONAL
}

EnumChangeLiensLogistiquesErrorCode ::= ENUMERATED
{
    no-error                             (0),
    error-invalid-automate               (1),
    error-invalid-automate-tc2           (2),
    error-invalid-automate-maintenance   (3),
    error-invalid-automate-sante         (4),
    error-invalid-automate-ravitaillement(5),
    error-unit-surrendered               (6)
}

MsgChangeLiensLogistiquesAck ::= SEQUENCE
{
    oid-automate       Automate,
    oid-tc2            Automate OPTIONAL,
    oid-maintenance    Automate OPTIONAL,
    oid-sante          Automate OPTIONAL,
    oid-ravitaillement Automate OPTIONAL,
    error-code         EnumChangeLiensLogistiquesErrorCode   
}

--
MsgChangeAutomate ::= SEQUENCE
{
    oid-pion     Agent,
    oid-automate Automate
}

EnumChangeAutomateErrorCode ::= ENUMERATED
{
    no-error                  (0),
    error-invalid-pion        (1),
    error-invalid-automate    (2),
    error-camps-incompatibles (3)
}

MsgChangeAutomateAck ::= SEQUENCE
{
    oid-pion     Agent,
    oid-automate Automate,
    error-code   EnumChangeAutomateErrorCode
}

-- INIT

MsgAutomateCreation ::= SEQUENCE
{
    oid-automate             Automate,
    type-automate            TypeAutomate,
    nom                      VisibleString,
    oid-camp                 Camp,
    oid-groupe-connaissance  OID,
    oid-tc2                  Automate OPTIONAL,
    oid-maintenance          Automate OPTIONAL,
    oid-sante                Automate OPTIONAL,
    oid-ravitaillement       Automate OPTIONAL
}

MsgPionCreation ::= SEQUENCE
{
    oid-pion        Agent,
    type-pion       TypePion,
    nom             VisibleString,
    oid-automate    Automate    
}

END -- ScipioHierarchie
