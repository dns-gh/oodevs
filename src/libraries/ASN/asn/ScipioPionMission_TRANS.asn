--
-- file name : ScipioPionMission_Rens.asn
--

ScipioPionMission_TRANS DEFINITIONS AUTOMATIC TAGS ::= BEGIN

IMPORTS Point FROM ScipioBase;

Mission-Pion-TRANS-EtablirGererLiaison ::= SEQUENCE
{
    position-deploiement Point
}

END -- ScipioPionMission_TRANS
