--
-- file name : ScipioPionMission_Misc.asn
--
-- Messages des différentes missions pion génériques et tests
--

ScipioAutomateMission_Misc DEFINITIONS AUTOMATIC TAGS ::= BEGIN

IMPORTS ListAgent, Agent, KnowledgeAgent, Direction, OID, CoordUTM, Point, Itineraire, ListPolygon, ListLocalisation, ListPoint, EnumUnitIdentificationLevel, Segment, GDH FROM ScipioBase
IMPORTS EnumObjectType FROM ScipioObject;

Mission-Automate-Test-MoveTo ::= SEQUENCE
{
    itineraire Itineraire
}

Mission-Automate-Decrocher ::= SEQUENCE
{
	point-regroupement  Polygon
}

Mission-Automate-ReleverSurPlace ::= SEQUENCE
{
	compagnie-a-relever Automate,
	zone-installation 	Polygon
}

Mission-Automate-FaireMouvement ::= SEQUENCE
{
    itineraire      Itineraire
}

Mission-Automate-SeFaireDecontaminer ::= SEQUENCE
{
	zone-arrivee			Polygon, 
	site-decontamination 	KnowledgeObject
}

Mission-Automate-Franchir ::= SEQUENCE
{
	pont-flottant	KnowledgeObject,
	zone-arrivee    Polygon
}

Mission-Automate-Stationner ::= SEQUENCE
{
	zone-attente Polygon
}

Mission-Automate-SeFaireTransporter ::= SEQUENCE
{
	zone-embarquement Polygon
}

Mission-Automate-Transporter ::= SEQUENCE
{
    unites-a-transporter            ListAgent,
    point-debarquement              Point,
    point-embarquement              Point,
    avec-materiel                   BOOLEAN DEFAULT FALSE
}

Mission-Automate-SeRecompleter ::= SEQUENCE
{
	zone-ravitaillement Polygon
}

Mission-Automate-SeRendre ::= SEQUENCE
{
}

Mission-Automate-FaireMouvementVersCampRefugies ::= SEQUENCE
{
}

-- Population

Mission-Automate-InterdireFranchissementPopulations ::= SEQUENCE
{
    points ListPoint
}

Mission-Automate-FiltrerPopulations ::= SEQUENCE
{
    points ListPoint
}

Mission-Automate-CanaliserPopulations ::= SEQUENCE
{
    zones ListLocalisation
}

Mission-Automate-ControlerPopulationsDansZone ::= SEQUENCE
{
    zones ListPolygon
}

Mission-Automate-SecuriserZoneContrePopulations ::= SEQUENCE
{
    points ListPoint
}

-- ASY

Mission-Automate-ASY-CommettreExactionsSurPopulationDansZone ::= SEQUENCE
{
    zones ListPolygon
}


-- Missions génériques
Mission-Automate-Generique ::= SEQUENCE
{
    zones                ListPolygon,
    points               ListPoint,
    itineraires          ListItineraire,
    unites               ListAgent,
    automates            ListAutomate,
    connaissances-agents ListKnowledgeAgent,
    connaissances-objets ListKnowledgeObject
}

END -- ScipioAutomateMission_Misc
