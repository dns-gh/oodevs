--
-- file name : ScipioBase.asn
--
-- Types de base
--

ScipioBase DEFINITIONS AUTOMATIC TAGS ::= BEGIN

--
-- Géométrie
--
EnumTypeLocalisation ::= ENUMERATED
{ 
    circle   (0), -- Circle
    ellipse  (1), -- Ellipse
    line     (2), -- Line 
    polygon  (3), -- Polygon
    point    (4), -- Point
    sector   (5)  -- Sector
}

CoordUTM ::= OCTET STRING (SIZE(15))

Localisation ::= SEQUENCE 
{
    type            EnumTypeLocalisation,
    vecteur-point   SEQUENCE OF CoordUTM
}

Point      ::= Localisation (WITH COMPONENTS {...,type(point)})
Line       ::= Localisation (WITH COMPONENTS {...,type(line)})
Itineraire ::= Localisation (WITH COMPONENTS {...,type(line)})
Polygon    ::= Localisation (WITH COMPONENTS {...,type(polygon)})
Segment    ::= Localisation (WITH COMPONENTS {type(line)   , vecteur-point (SIZE(2))})
Circle	   ::= Localisation (WITH COMPONENTS {type(circle) , vecteur-point (SIZE(2))}) -- Format : centre, point sur le cercle
Ellipse	   ::= Localisation (WITH COMPONENTS {type(ellipse), vecteur-point (SIZE(3))}) -- Format : centre, point petit axe, point grand axe
Sector	   ::= Localisation (WITH COMPONENTS {type(sector) , vecteur-point (SIZE(3))}) -- Format : centre, point 1, point 2 dans le sens trigo

ListLocalisation ::= SEQUENCE OF Localisation
ListPolygon      ::= SEQUENCE OF Polygon
ListItineraire   ::= SEQUENCE OF Itineraire
ListPoint        ::= SEQUENCE OF Point

--
-- Types
--
OID                     ::= INTEGER
ListOID                 ::= SEQUENCE OF OID
TirPion                 ::= OID
TirPopulation           ::= OID
Agent                   ::= OID
Automate                ::= OID
Population              ::= OID
Camp                    ::= OID
Formation               ::= OID
KnowledgeGroup          ::= OID
KnowledgeAgent          ::= OID
KnowledgeObject         ::= OID
KnowledgePopulation     ::= OID
ListAutomate            ::= SEQUENCE OF Automate 
ListAgent               ::= SEQUENCE OF Agent
ListKnowledgeAgent      ::= SEQUENCE OF KnowledgeAgent
ListKnowledgeObject     ::= SEQUENCE OF KnowledgeObject
ListCamp                ::= SEQUENCE OF Camp
ListPopulation          ::= SEQUENCE OF Population
ListFormation           ::= SEQUENCE OF Formation
TypeEquipement          ::= OID
TypeDotation            ::= OID
TypeDotationTrancheD    ::= OID
TypePanne               ::= OID
TypePion                ::= OID
TypeAutomate            ::= OID
TypePopulation          ::= OID
Pourcentage             ::= INTEGER(0..100)
PourcentageLibre        ::= INTEGER
Hauteur                 ::= INTEGER
Altitude                ::= INTEGER
Vitesse                 ::= INTEGER
Angle                   ::= INTEGER(0..360)
Direction               ::= INTEGER(0..<360)
GDH                     ::= SEQUENCE 
{
    datation        INTEGER,
    qualificatif    EnumGDH_Qualificatif 
}

EnumFamilleDotation ::= ENUMERATED
{
    munition (0),
    carburant(1),
    explosif (2),
    mine     (3),
    barbele  (4),
    piece    (5),
    ration   (6)
}

EnumFamilleMunition ::= ENUMERATED
{
    obus        (0),
    missile-air (1),
    missile-sol (2),
    mitraille   (3)
}

EnumGDH_Qualificatif ::= ENUMERATED
{
    at          (0),
    after       (1),
    as-of       (2),
    before      (3),
    cleared     (4),
    due         (5),
    end         (6),
    off         (7),
    on          (8),
    since       (9),
    start       (10),
    until       (11),
    wef         (12)
}

EnumUnitIdentificationLevel ::= ENUMERATED
{
    identifiee (0),
    reconnue   (1),
    detectee   (2),
    signale    (3) 
}

EnumNatureLevel ::= ENUMERATED
{
    none        (0),  -- None
    o           (1),  -- Team
    oo          (2),  -- Group/Patrol/Squad
    ooo         (3),  -- Section/platoon
    i           (4),  -- Company
    ii          (5),  -- Battalion
    iii         (6),  -- Regiment
    x           (7),  -- Brigade
    xx          (8),  -- Division
    xxx         (9),  -- Army corps
    xxxx        (10), -- Field army (obsolete)
    xxxxx       (11)  -- Army group/front (obsolete)
}

NatureAtlas ::= BIT STRING 
{ 
    blinde          (0), 
    ass             (1), 
    pc              (2), 
    log             (3), 
    mortier         (4), 
    lance-roquette  (5), 
    vehicule        (6), 
    personnel-a-pied(7), 
    helicoptere     (8), 
    indefini        (9), 
    asa             (10),
    none            (11) 
}

EnumHumanWound ::= ENUMERATED 
{
    non-blesse            (0),
    mort                  (1),
    blesse-urgence-1      (2),
    blesse-urgence-2      (3),
    blesse-urgence-3      (4),
    blesse-urgence-extreme(5)
}

EnumHumanRank ::= ENUMERATED
{
    officier    (0),
    sous-officer(1),
    mdr         (2)
}
                  

END -- ScipioBase
