--
-- file name : ScipioCR.asn
--
-- Messages de gestion des comptes rendus
--

ScipioCR DEFINITIONS AUTOMATIC TAGS ::= BEGIN

IMPORTS Objet, EnumUnitIdentificationLevel, KnowledgeAgent, KnowledgeObject, KnowledgePopulation, Agent, OID, CoordUTM, Line FROM ScipioBase
IMPORTS EnumPopulationAttitude From ScipioPopulation
IMPORTS EnumTypeLima FROM ScipioLimaLimite;

CR-RAS                                      ::= NULL
                                            
-- Obstacle                                 
CR-EnPosteFaceAObstacle                     ::= KnowledgeObject
CR-EnContournementObstacle                  ::= NULL
                                            
-- Phases de mission                        
CR-MissionImpossible                        ::= NULL
CR-ProgressionSurAxe                        ::= NULL
CR-ProgressionVersPosition                  ::= NULL
CR-ArriveSurPosition                        ::= NULL
CR-ReconnaissancePoint                      ::= NULL
CR-EnPosteFaceADirectionDangereuse          ::= NULL
CR-EnJalonnement                            ::= NULL
CR-PreparationMission                       ::= SEQUENCE
{
    delai INTEGER OPTIONAL
}
CR-DebutMission                             ::= NULL
CR-FinMission                               ::= NULL
CR-DispositifInstalle                       ::= NULL
CR-EnPosition                               ::= NULL
CR-ObjectifAtteint                          ::= NULL
CR-Debouche                                 ::= NULL 
CR-RejointUnite                             ::= NULL
CR-EscorteUnite                             ::= NULL
CR-EnFreinage                               ::= NULL
CR-Assaut                                   ::= NULL
CR-EnCouverture                             ::= NULL
CR-EnEclairage                              ::= NULL
CR-EnManoeuvreRavitaillement                ::= NULL
CR-SurPIA                                   ::= Agent
CR-PassageSurPIA                            ::= NULL
CR-UniteRecueillie                          ::= Agent
CR-EnCoursDeFranchissement                  ::= NULL
CR-AttenteOrdrePoursuivre                   ::= NULL
CR-AttenteOrdreDeboucher                    ::= NULL

-- RENS
CR-DebutControleZone                        ::= NULL
CR-FinControleZone                          ::= NULL
CR-DebutSurveillance                        ::= NULL
CR-FinSurveillance                          ::= NULL
CR-EnInfiltration                           ::= NULL
CR-EnExfiltration                           ::= NULL
CR-AttenteConditionFavorablePourInfiltration::= NULL
CR-DroneLance                               ::= NULL
CR-DroneEnExploitation                      ::= NULL
CR-DroneExploite                            ::= NULL
CR-DroneDisponible                          ::= NULL
CR-DebutMiseEnOeuvreDrone                   ::= NULL
CR-FinMiseEnOeuvreDrone                     ::= NULL
CR-ActivationBrouillage                     ::= NULL
CR-DesactivationBrouillage                  ::= NULL
CR-ActivationSystemeEcoute                  ::= NULL
CR-DesactivationSystemeEcoute               ::= NULL
CR-ActivationSystemeEcouteRadar             ::= NULL
CR-DesactivationSystemeEcouteRadar          ::= NULL
CR-DebutLiaison                             ::= NULL
CR-FinLiaison                               ::= NULL
CR-EtablissementLiaisonImpossible           ::= NULL
CR-UniteTropDistante                        ::= Agent
CR-EnregistrementDonnes                     ::= NULL
CR-ExploitationDonnees                      ::= NULL
CR-ExtractionDonnes                         ::= NULL
                                           
-- Ennemi                                   
CR-Fixe                                     ::= NULL
CR-EnEsquive                                ::= NULL
CR-PriseContact                             ::= NULL
CR-RuptureContact                           ::= NULL
CR-PrecisionContact                         ::= KnowledgeAgent
CR-EnnemiDetruit                            ::= KnowledgeAgent
CR-PrisAPartieParTirDirect                  ::= NULL
CR-PrisSousTirArtillerie                    ::= NULL
CR-PointTenuParEni                          ::= KnowledgeAgent
CR-ProgressionVersEni                       ::= KnowledgeAgent
CR-Decroche                                 ::= NULL
CR-EniSurObjectif                           ::= KnowledgeAgent
CR-Riposte                                  ::= NULL
CR-PretPourEngagementSurEnnemi              ::= NULL
                                            
-- Ami          
CR-Releve                                   ::= Agent                            
CR-SuitUnite                                ::= NULL
CR-PasseEnAppui                             ::= NULL
CR-EnAppui                                  ::= NULL
                                                                                                                                
-- Etat du pion                             
CR-NonOperationnel                          ::= NULL
CR-Operationnel                             ::= NULL
                                                                                     
-- Deplacement                              
CR-AmbianceVitesse                          ::= NULL
CR-AmbianceSurete                           ::= NULL
CR-SurLima                                  ::= EnumTypeLima
                                            
-- Genie                                    
CR-DebutAmenagementBerges                   ::= NULL      
CR-FinAmenagementBerges                     ::= NULL        
CR-ObstacleEnAttenteActivation              ::= KnowledgeObject
CR-DebutTravaux                             ::= NULL
CR-FinTravaux                               ::= NULL
CR-ObstacleDegage                           ::= NULL
CR-OrganisationChantier                     ::= NULL
CR-DesorganisationChantier                  ::= NULL
CR-ReconnaissancePositionObstacle           ::= NULL
CR-ContournementRealise                     ::= NULL
CR-AttenteRenforcement                      ::= NULL
CR-DebutExploitationSiteFranchissement      ::= NULL
CR-FinExploitationSiteFranchissement        ::= NULL
CR-ReussiteRenforcement                     ::= SEQUENCE
{
    pion-renforcant     Agent,
    automate-renforce   Agent
}
CR-EchecRenforcement                        ::= SEQUENCE
{
    pion-renforcant     Agent,
    automate-renforce   Agent
}
                                           
-- Log          
CR-RegimeMaintenanceDelaiDepasse            ::= NULL
CR-SectionDeployee                          ::= NULL
CR-ANouveauDisponibleApresReparation        ::= NULL
CR-MaterielRepareSurPlace                   ::= TypeEquipement
CR-MaterielRetourDeMaintenance              ::= TypeEquipement
CR-DemandeRavitaillementDotations           ::= NULL
CR-DemandeRavitaillementStock               ::= NULL
CR-DemandeEvacuationSanitaire               ::= NULL
CR-DemandeEvacuationMateriel                ::= NULL
CR-AllocationConsentieBientotEpuisee        ::= TypeDotation
CR-DepassementCapaciteStockage              ::= NULL
CR-SeuilLogistiqueDotationDepasse           ::= TypeDotation
CR-SeuilLogistiqueStockDepasse              ::= TypeDotation
CR-RavitaillementDotationsEffectue          ::= NULL
CR-RavitaillementStockEffectue              ::= NULL
CR-RavitaillementDotationsAnnule            ::= NULL
CR-RavitaillementStockAnnule                ::= NULL
CR-HumainRetourDeSante                      ::= NULL
CR-AlerteDisponibiliteMoyensReleve          ::= NULL
CR-AlerteDisponibiliteMoyensRamassage       ::= NULL
CR-AlerteDisponibiliteMedecins              ::= NULL
CR-AlerteDisponibiliteRemorqueurs           ::= NULL
CR-AlerteDisponibiliteReparateurs           ::= NULL
CR-AlerteDisponibiliteVecteurs              ::= NULL

CR-PretMaterielEnCours                              ::= NULL
CR-PretMaterielAnnule                               ::= NULL
CR-PretMaterielEffectue                             ::= NULL
CR-PretMaterielPartiellementEffectue                ::= NULL
CR-PretMaterielImpossible                           ::= NULL
CR-RecuperationMaterielPreteEffectuee               ::= NULL
CR-RecuperationMaterielPretePartiellementEffectuee  ::= NULL
CR-RecuperationMaterielPreteImpossible              ::= NULL
CR-MaterielPrete                                    ::= NULL
CR-MaterielRendu                                    ::= NULL

CR-Convoi-DeplacementVersPointChargement    ::= NULL
CR-Convoi-ChargementEnCours                 ::= NULL
CR-Convoi-ChargementEffectue                ::= NULL
CR-Convoi-DeplacementVersPointDechargement  ::= NULL
CR-Convoi-DechargementEnCours               ::= NULL
CR-Convoi-DechargementEffectue              ::= NULL
CR-Convoi-Retour                            ::= NULL


-- ALAT / Transport / Embarquement
CR-EnCoursRavitaillement                    ::= NULL
CR-RavitaillementTermine                    ::= NULL
CR-HelicoptereEnObservation                 ::= NULL
CR-PerteInfoGuidage                         ::= NULL
CR-TransportUnitePasPrete                   ::= Agent
CR-TransportUnitePrete                      ::= Agent
CR-TransportEnCours                         ::= NULL
CR-TransportEmbarquement                    ::= NULL
CR-TransportDebarquement                    ::= NULL
CR-TransportImpossiblePasDeMoyens           ::= NULL
CR-VehiculeLaisseSurPosition                ::= NULL
CR-RejointPositionEmbarquement              ::= NULL
CR-EnAttenteTransporteurs                   ::= NULL

-- NBC
CR-ContamineNBC                             ::= NULL
CR-DecontamineNBC                           ::= NULL
CR-TenueProtectionNBCMise                   ::= NULL
CR-TenueProtectionNBCEnlevee                ::= NULL
CR-AlerteNBCNiveau4                         ::= NULL
CR-FinAlerteNBCNiveau4                      ::= NULL
CR-SiteDecontaminationAnime                 ::= NULL
CR-SiteDecontaminationDesactive             ::= NULL 
CR-DemandeDecontamination                   ::= NULL
CR-ZoneReconnue                             ::= NULL
CR-ZoneDecontaminee                         ::= NULL
CR-SiteROTAReconnu                          ::= NULL
CR-IncidentNBCTermine                       ::= NULL  -- réparation site ROTA 
CR-UniteDecontaminee                        ::= Agent -- pion ami CR explicte de decontamination
CR-SiteSature                               ::= NULL
CR-DebutMesure                              ::= NULL
CR-FinMesure                                ::= NULL
                                          
-- Artillerie                               
CR-ReconnaissanceTerminee                   ::= NULL 
CR-ReconnaissanceInitialeTerminee           ::= NULL 
CR-RejointPlotRavitaillement                ::= NULL
CR-PremierCoupParti                         ::= NULL
CR-TirExecute                               ::= NULL
CR-TirHorsDePortee                          ::= NULL
CR-TirImpossiblePlusDeMunitions             ::= NULL
CR-TirAnnule                                ::= NULL
CR-ChangementDePosition                     ::= NULL
CR-DebutInstallation                        ::= NULL
CR-FinInstallation                          ::= NULL
CR-PretPourConduiteTir                      ::= NULL
CR-ReceptionOrdreDeFeu                      ::= NULL
CR-PretAuTir                                ::= NULL
CR-ObservationTirIndirect                   ::= TirPion -- OID du tir observé
CR-ZoneImplantationOccupee                  ::= NULL
CR-InstallationSurZoneImplantation          ::= NULL

-- Population / reddition
CR-PresencePopulation                        ::= NULL
CR-OrientationPopulationVersCampRefugies     ::= NULL
CR-PasDeCampRefugiesDisponible               ::= NULL
CR-PresenceEnnemiRendu                       ::= NULL
CR-OrientationEnnemiRenduVersCampPrisonniers ::= NULL
CR-PasDeCampPrisonniersDisponible            ::= NULL
CR-Rendu                                     ::= NULL

-- Adaptation
CR-Trace    ::= VisibleString
CR-TraceID  ::= INTEGER

-- Evenements exceptionnels
CR-TirDansZoneInterdite              ::= NULL
CR-TirIndirectFratricide             ::= NULL
CR-TirIndirectSurPopulation          ::= NULL
CR-TirSurCampAmi                     ::= Agent -- Agent = Tiré
CR-TireParCampAmi                    ::= Agent -- Agent = Tireur
CR-TirSurCampNeutre                  ::= Agent -- Agent = Tiré
CR-TireParCampNeutre                 ::= Agent -- Agent = Tireur
CR-TirSurCivil                       ::= Agent -- Agent = Tiré
CR-TireParCivil                      ::= Agent -- Agent = Tireur
CR-DestructionPC                     ::= NULL
CR-DecesBlesse                       ::= NULL
CR-DecesBlessePendantTransport       ::= NULL
CR-DecesBlessePendantHospitalisation ::= NULL

-- New
CR-MissionImpossibleUnitesSubordonneesNonOperationnelles ::= NULL
CR-MissionImpossibleLimaInvalide                         ::= NULL
CR-MissionImpossibleZoneHorsFuseau                       ::= NULL
CR-RapportDeForceDefavorable                             ::= NULL
CR-TerrainDifficile                                      ::= NULL -- Moteur
CR-PlusDeCarburant                                       ::= NULL -- Moteur
CR-DispositifDisperse                                    ::= NULL
CR-DebutNeutralisation                                   ::= NULL -- Un ou plusieurs pions de l'automate a subi un tir indirect et est (sont) neutralisé(s)
CR-FinNeutralisation                                     ::= NULL 
CR-DebutSilenceRadio                                     ::= NULL
CR-FinSilenceRadio                                       ::= NULL
CR-DebutSilenceRadar                                     ::= NULL
CR-FinSilenceRadar                                       ::= NULL
CR-TirRestreint                                          ::= NULL
CR-TirInterdit                                           ::= NULL
CR-TirLibre                                              ::= NULL
CR-UniteDetectee                                         ::= KnowledgeAgent
CR-UniteAmieReconnue                                     ::= KnowledgeAgent
CR-UniteEnnemieReconnue                                  ::= KnowledgeAgent
CR-UniteNeutreReconnue                                   ::= KnowledgeAgent
CR-UniteAmieIdentifiee                                   ::= KnowledgeAgent
CR-UniteEnnemieIdentifiee                                ::= KnowledgeAgent
CR-UniteNeutreIdentifiee                                 ::= KnowledgeAgent
CR-ObjetDetecte                                          ::= KnowledgeObject

-- Reaction Populations
CR-EmploiForceInterdit                                   ::= NULL
CR-MaintienADistanceParMoyensNonLetaux                   ::= NULL
CR-DispersionParMoyensDeDefenseActifs                    ::= NULL
CR-ArmesLetalesAutorisees                                ::= NULL
CR-PopulationDetectee                                    ::= KnowledgePopulation
CR-PriseAPartieParPopulation                             ::= KnowledgePopulation
CR-RiposteContrePopulation                               ::= KnowledgePopulation
CR-PopulationDangereuseAProximite                        ::= NULL
CR-EsquiveFaceAPopulation                                ::= NULL
CR-DecrochageFaceAPopulation                             ::= NULL
CR-MiseEnPlaceControleDeFoule                            ::= NULL
CR-MiseEnPlaceFiltrage                                   ::= NULL
CR-AnimationBarrage                                      ::= NULL
CR-AnimationCanalisation                                 ::= NULL
CR-CollecteRenseignementsSurPopulations                  ::= NULL
CR-PopulationReconnue                                    ::= NULL
CR-SituationDifficilementTenableFaceAPopulation          ::= NULL
CR-UtilisationArmesNonLetalesFaceAPopulation             ::= NULL
CR-UtilisationMoyensDefenseActifsFaceAPopulation         ::= NULL
CR-UtilisationArmementsFaceAPopulation                   ::= NULL
CR-DebutInterventionFaceAPopulation                      ::= EnumPopulationAttitude
CR-PopulationVictimeAffrontements                        ::= SEQUENCE
{
    victimes      INTEGER,
    dont-blesses  INTEGER
}

-- Populations provisions
CR-AttitudePopulation                                    ::= EnumPopulationAttitude
CR-AggravationAttitude                                   ::= NULL
CR-AffrontementAvecForcesEnnemies                        ::= NULL
CR-PopulationTemporairementControlee                     ::= NULL
CR-PopulationTemporairementRepoussee                     ::= NULL
CR-RepriseDesAffrontements                               ::= NULL
CR-AgressionDePopulation                                 ::= KnowledgePopulation
CR-AgressionParPopulation                                ::= KnowledgePopulation
CR-RiposteContreAgressionParPopulation                   ::= KnowledgePopulation
CR-AttaqueInstallation                                   ::= NULL
CR-EnStationnement                                       ::= NULL
CR-Bloquee                                               ::= NULL
CR-Filtree                                               ::= NULL
CR-AttentatTerroristeDansPopulation                      ::= NULL
CR-PopulationVictimeExplosionMines                       ::= SEQUENCE
{
    victimes      INTEGER,
    dont-blesses  INTEGER
}




-- Menaces Asymetriques
CR-ExecutionAttentat                                     ::= NULL

EnumTypeCR ::= ENUMERATED
{
    message                 (0),
    operationel             (1),
    evenement-exceptionnel  (2),
    warning                 (3)
}

MsgCR ::= SEQUENCE
{
    unit-id   OID, -- Automate, pion ou population
    type-cr   EnumTypeCR,
    cr        CHOICE
    {
        cr-ras                                                          CR-RAS,                                      
                                                                                                        
        -- obstacle                                     
        cr-en-poste-face-a-obstacle                                     CR-EnPosteFaceAObstacle,                     
        cr-en-contournement-obstacle                                    CR-EnContournementObstacle,                  
                                                                                                        
        -- phases de mission                            
        cr-mission-impossible                                           CR-MissionImpossible,                        
        cr-progression-sur-axe                                          CR-ProgressionSurAxe,                        
        cr-progression-vers-position                                    CR-ProgressionVersPosition,              
        cr-arrive-sur-position                                          CR-ArriveSurPosition,                    
        cr-reconnaissance-point                                         CR-ReconnaissancePoint,               
        cr-en-poste-face-a-direction-dangereuse                         CR-EnPosteFaceADirectionDangereuse,         
        cr-en-jalonnement                                               CR-EnJalonnement,                            
        cr-preparation-mission                                          CR-PreparationMission,
        cr-debut-mission                                                CR-DebutMission,                             
        cr-fin-mission                                                  CR-FinMission,                               
        cr-dispositif-installe                                          CR-DispositifInstalle,                       
        cr-en-position                                                  CR-EnPosition,                               
        cr-objectif-atteint                                             CR-ObjectifAtteint,                          
        cr-debouche                                                     CR-Debouche,                                         
        cr-rejoint-unite                                                CR-RejointUnite,
        cr-escorte-unite                                                CR-EscorteUnite,
        cr-en-freinage                                                  CR-EnFreinage,
        cr-assaut                                                       CR-Assaut,
        cr-en-couverture                                                CR-EnCouverture,
        cr-en-eclairage                                                 CR-EnEclairage,
        cr-en-manoeuvre-ravitaillement                                  CR-EnManoeuvreRavitaillement,
        cr-sur-pia                                                      CR-SurPIA,                                   
        cr-passage-sur-pia                                              CR-PassageSurPIA,
        cr-unite-recueillie                                             CR-UniteRecueillie,                          
        cr-en-cours-de-franchissement                                   CR-EnCoursDeFranchissement,    
        cr-attente-ordre-poursuivre                                     CR-AttenteOrdrePoursuivre,
        cr-attente-ordre-deboucher                                      CR-AttenteOrdreDeboucher,
        
        -- ennemi                                        
        cr-fixe                                                         CR-Fixe,
        cr-en-esquive                                                   CR-EnEsquive,
        cr-prise-contact                                                CR-PriseContact,                    
        cr-rupture-contact                                              CR-RuptureContact,                  
        cr-precision-contact                                            CR-PrecisionContact,                         
        cr-ennemi-detruit                                               CR-EnnemiDetruit,                            
        cr-pris-a-partie-par-tir-direct                                 CR-PrisAPartieParTirDirect,                             
        cr-pris-sous-tir-artillerie                                     CR-PrisSousTirArtillerie,
        cr-point-tenu-par-eni                                           CR-PointTenuParEni,                          
        cr-progression-vers-eni                                         CR-ProgressionVersEni,                       
        cr-decroche                                                     CR-Decroche,                                 
        cr-eni-sur-objectif                                             CR-EniSurObjectif,                           
        cr-riposte                                                      CR-Riposte,            
        cr-pret-pour-engagement-sur-ennemi                              CR-PretPourEngagementSurEnnemi,
                                                                                                
        -- rens                                          
        cr-debut-controle-zone                                          CR-DebutControleZone,                           
        cr-fin-controle-zone                                            CR-FinControleZone,                                  
        cr-debut-surveillance                                           CR-DebutSurveillance,                           
        cr-fin-surveillance                                             CR-FinSurveillance,                           
        cr-en-infiltration                                              CR-EnInfiltration,                           
        cr-en-exfiltration                                              CR-EnExfiltration,                           
        cr-attente-condition-favorable-pour-infiltration                CR-AttenteConditionFavorablePourInfiltration,
        cr-drone-lance                                                  CR-DroneLance,
        cr-drone-en-exploitation                                        CR-DroneEnExploitation,
        cr-drone-exploite                                               CR-DroneExploite,
        cr-drone-disponible                                             CR-DroneDisponible,
        cr-debut-mise-en-oeuvre-drone                                   CR-DebutMiseEnOeuvreDrone,
        cr-fin-mise-en-oeuvre-drone                                     CR-FinMiseEnOeuvreDrone,                
        cr-activation-brouillage                                        CR-ActivationBrouillage,
        cr-desactivation-brouillage                                     CR-DesactivationBrouillage,
        cr-activation-systeme-ecoute                                    CR-ActivationSystemeEcoute,
        cr-desactivation-systeme-ecoute                                 CR-DesactivationSystemeEcoute,
        cr-activation-systeme-ecoute-radar                              CR-ActivationSystemeEcouteRadar,
        cr-desactivation-systeme-ecoute-radar                           CR-DesactivationSystemeEcouteRadar,       
        cr-debut-liaison                                                CR-DebutLiaison,
        cr-fin-liaison                                                  CR-FinLiaison,
        cr-etablissement-liaison-impossible                             CR-EtablissementLiaisonImpossible,
        cr-unite-trop-distante                                          CR-UniteTropDistante,
        cr-enregistrement-donnes                                        CR-EnregistrementDonnes,
        cr-exploitation-donnees                                         CR-ExploitationDonnees,
        cr-extraction-donnes                                            CR-ExtractionDonnes,                            
                                                                                                        
        -- ami                                           
        cr-releve                                                       CR-Releve,                                   
        cr-suit-unite                                                   CR-SuitUnite,                               
        cr-passe-en-appui                                               CR-PasseEnAppui,                             
        cr-en-appui                                                     CR-EnAppui,                                  
                                                                                                                                                                                                           
        -- etat du pion        
        cr-non-operationnelle                                           CR-NonOperationnel,
        cr-operationnelle                                               CR-Operationnel,
                                                                                                        
        -- deplacement         
        cr-ambiance-vitesse                                             CR-AmbianceVitesse,                          
        cr-ambiance-surete                                              CR-AmbianceSurete,                           
        cr-sur-lima                                                     CR-SurLima,                                  
                                                                                                        
        -- genie                                    
        cr-debut-travaux                                                CR-DebutTravaux,                             
        cr-fin-travaux                                                  CR-FinTravaux,                          
        cr-obstacle-degage                                              CR-ObstacleDegage,                           
        cr-organisation-chantier                                        CR-OrganisationChantier,                     
        cr-desorganisation-chantier                                     CR-DesorganisationChantier,                  
        cr-reconnaissance-position-obstacle                             CR-ReconnaissancePositionObstacle,           
        cr-contournement-realise                                        CR-ContournementRealise,                     
        cr-attente-renforcement                                         CR-AttenteRenforcement,                      
        cr-debut-exploitation-site-franchissement                       CR-DebutExploitationSiteFranchissement,
        cr-fin-exploitation-site-franchissement                         CR-FinExploitationSiteFranchissement,
        cr-reussite-renforcement                                        CR-ReussiteRenforcement,                     
        cr-echec-renforcement                                           CR-EchecRenforcement,
        cr-obstacle-en-attente-activation                               CR-ObstacleEnAttenteActivation,        
        cr-debut-amenagement-berges                                     CR-DebutAmenagementBerges,      
        cr-fin-amenagement-berges                                       CR-FinAmenagementBerges,        
                                                                                                                                                                                                           
        -- log   
        cr-regime-maintenance-delai-depasse                             CR-RegimeMaintenanceDelaiDepasse,
        cr-section-deployee                                             CR-SectionDeployee,       
        cr-a-nouveau-disponible-apres-reparation                        CR-ANouveauDisponibleApresReparation,
        cr-materiel-retour-de-maintenance                               CR-MaterielRetourDeMaintenance,
        cr-materiel-repare-sur-place                                    CR-MaterielRepareSurPlace,
        cr-demande-ravitaillement-dotations                             CR-DemandeRavitaillementDotations,
        cr-demande-ravitaillement-stock                                 CR-DemandeRavitaillementStock,
        cr-demande-evacuation-sanitaire                                 CR-DemandeEvacuationSanitaire,
        cr-demande-evacuation-materiel                                  CR-DemandeEvacuationMateriel,
        cr-allocation-consentie-bientot-epuisee                         CR-AllocationConsentieBientotEpuisee,
        cr-depassement-capacite-stockage                                CR-DepassementCapaciteStockage,
        cr-seuil-logistique-dotation-depasse                            CR-SeuilLogistiqueDotationDepasse,
        cr-seuil-logistique-stock-depasse                               CR-SeuilLogistiqueStockDepasse,
        cr-ravitaillement-dotations-effectue                            CR-RavitaillementDotationsEffectue,
        cr-ravitaillement-stock-effectue                                CR-RavitaillementStockEffectue,
        cr-ravitaillement-dotations-annule                              CR-RavitaillementDotationsAnnule,
        cr-ravitaillement-stock-annule                                  CR-RavitaillementStockAnnule,
        cr-humain-retour-de-sante                                       CR-HumainRetourDeSante,             
        cr-alerte-disponibilite-moyens-releve                           CR-AlerteDisponibiliteMoyensReleve,
        cr-alerte-disponibilite-moyens-ramassage                        CR-AlerteDisponibiliteMoyensRamassage,
        cr-alerte-disponibilite-medecins                                CR-AlerteDisponibiliteMedecins,
        cr-alerte-disponibilite-remorqueurs                             CR-AlerteDisponibiliteRemorqueurs,
        cr-alerte-disponibilite-reparateurs                             CR-AlerteDisponibiliteReparateurs,
        cr-alerte-disponibilite-vecteurs                                CR-AlerteDisponibiliteVecteurs,
        cr-pret-materiel-en-cours                                       CR-PretMaterielEnCours,
        cr-pret-materiel-annule                                         CR-PretMaterielAnnule,
        cr-pret-materiel-effectue                                       CR-PretMaterielEffectue,
        cr-pret-materiel-impossible                                     CR-PretMaterielImpossible,
        cr-pret-materiel-partiellement-effectue                         CR-PretMaterielPartiellementEffectue,
        cr-recuperation-materiel-prete-impossible                       CR-RecuperationMaterielPreteImpossible,
        cr-recuperation-materiel-prete-effectuee                        CR-RecuperationMaterielPreteEffectuee,
        cr-recuperation-materiel-prete-partiellement-effectuee          CR-RecuperationMaterielPretePartiellementEffectuee,
        cr-materiel-prete                                               CR-MaterielPrete,
        cr-materiel-rendu                                               CR-MaterielRendu,
        cr-convoi-deplacement-vers-point-chargement                     CR-Convoi-DeplacementVersPointChargement,
        cr-convoi-chargement-en-cours                                   CR-Convoi-ChargementEnCours,               
        cr-convoi-chargement-effectue                                   CR-Convoi-ChargementEffectue,              
        cr-convoi-deplacement-vers-point-dechargement                   CR-Convoi-DeplacementVersPointDechargement,
        cr-convoi-dechargement-en-cours                                 CR-Convoi-DechargementEnCours,
        cr-convoi-dechargement-effectue                                 CR-Convoi-DechargementEffectue,            
        cr-convoi-retour                                                CR-Convoi-Retour,            
        
        -- LOG ALAT / ALAT
        cr-en-cours-ravitaillement                                      CR-EnCoursRavitaillement,
        cr-ravitaillement-termine                                       CR-RavitaillementTermine,
        cr-helicoptere-en-observation                                   CR-HelicoptereEnObservation,
        cr-perte-info-guidage                                           CR-PerteInfoGuidage,
        cr-transport-unite-pas-prete                                    CR-TransportUnitePasPrete,
        cr-transport-unite-prete                                        CR-TransportUnitePrete,
        cr-transport-en-cours                                           CR-TransportEnCours,
        cr-transport-embarquement                                       CR-TransportEmbarquement,
        cr-transport-debarquement                                       CR-TransportDebarquement,
        cr-transport-impossible-pas-de-moyens                           CR-TransportImpossiblePasDeMoyens,
        cr-vehicule-laisse-sur-position                                 CR-VehiculeLaisseSurPosition,
        cr-rejoint-position-embarquement                                CR-RejointPositionEmbarquement,
        cr-en-attente-transporteurs                                     CR-EnAttenteTransporteurs,  
                                                                                                
        -- nbc                                         
        cr-contamine-nbc                                                CR-ContamineNBC,                             
        cr-decontamine-nbc                                              CR-DecontamineNBC,                           
        cr-tenue-protection-nbc-mise                                    CR-TenueProtectionNBCMise,                   
        cr-tenue-protection-nbc-enlevee                                 CR-TenueProtectionNBCEnlevee,                
        cr-alerte-nbc-niveau-4                                          CR-AlerteNBCNiveau4,                                
        cr-fin-alerte-nbc-niveau-4                                      CR-FinAlerteNBCNiveau4,                                        
        cr-site-decontamination-anime                                   CR-SiteDecontaminationAnime,                 
        cr-site-decontamination-desactive                               CR-SiteDecontaminationDesactive,             
        cr-demande-decontamination                                      CR-DemandeDecontamination,                   
        cr-zone-reconnue                                                CR-ZoneReconnue,
        cr-zone-decontaminee                                            CR-ZoneDecontaminee,
        cr-site-rota-reconnu                                            CR-SiteROTAReconnu,
        cr-incident-nbc-termine                                         CR-IncidentNBCTermine,
        cr-unite-decontaminee                                           CR-UniteDecontaminee,
        cr-site-sature                                                  CR-SiteSature,
        cr-debut-mesure                                                 CR-DebutMesure,
        cr-fin-mesure                                                   CR-FinMesure,
                                                                                                    
        -- artillerie                                  
        cr-reconnaissance-terminee                                      CR-ReconnaissanceTerminee,                   
        cr-reconnaissance-initiale-terminee                             CR-ReconnaissanceInitialeTerminee,           
        cr-rejoint-plot-ravitaillement                                  CR-RejointPlotRavitaillement,                
        cr-premier-coup-parti                                           CR-PremierCoupParti,                         
        cr-tir-execute                                                  CR-TirExecute,                               
        cr-tir-hors-de-portee                                           CR-TirHorsDePortee,
        cr-tir-impossible-plus-de-munitions                             CR-TirImpossiblePlusDeMunitions,
        cr-tir-annule                                                   CR-TirAnnule,        
        cr-changement-de-position                                       CR-ChangementDePosition,                     
        cr-debut-installation                                           CR-DebutInstallation,                        
        cr-fin-installation                                             CR-FinInstallation,                        
        cr-pret-pour-conduite-tir                                       CR-PretPourConduiteTir,                      
        cr-observation-tir-indirect                                     CR-ObservationTirIndirect,                   
        cr-zone-implantation-occupee                                    CR-ZoneImplantationOccupee,
        cr-installation-sur-zone-implantation                           CR-InstallationSurZoneImplantation,
        cr-reception-ordre-de-feu                                       CR-ReceptionOrdreDeFeu, 
        cr-pret-au-tir                                                  CR-PretAuTir,  
        
        -- population / reddition
        cr-presence-population                                          CR-PresencePopulation,
        cr-orientation-population-vers-camp-refugies                    CR-OrientationPopulationVersCampRefugies,
        cr-pas-de-camp-refugies-disponible                              CR-PasDeCampRefugiesDisponible,
        cr-presence-ennemi-rendu                                        CR-PresenceEnnemiRendu,
        cr-orientation-ennemi-rendu-vers-camp-prisonniers               CR-OrientationEnnemiRenduVersCampPrisonniers,
        cr-pas-de-camp-prisonniers-disponible                           CR-PasDeCampPrisonniersDisponible,
        cr-rendu                                                        CR-Rendu,
                
        -- evt exceptionnels
        cr-tir-dans-zone-interdite                                      CR-TirDansZoneInterdite,
        cr-tir-sur-camp-ami                                             CR-TirSurCampAmi,
        cr-tire-par-camp-ami                                            CR-TireParCampAmi,
        cr-tir-sur-camp-neutre                                          CR-TirSurCampNeutre,
        cr-tire-par-camp-neutre                                         CR-TireParCampNeutre,
        cr-tir-sur-civil                                                CR-TirSurCivil,
        cr-tire-par-civil                                               CR-TireParCivil,
        cr-tir-indirect-fratricide                                      CR-TirIndirectFratricide,
        cr-tir-indirect-sur-population                                  CR-TirIndirectSurPopulation,
        cr-destruction-pc                                               CR-DestructionPC,
        cr-deces-blesse                                                 CR-DecesBlesse,
        cr-deces-blesse-pendant-transport                               CR-DecesBlessePendantTransport,
        cr-deces-blesse-pendant-hospitalisation                         CR-DecesBlessePendantHospitalisation,        
        
        -- New
        cr-mission-impossible-unites-subordonnees-non-operationnelles   CR-MissionImpossibleUnitesSubordonneesNonOperationnelles,
        cr-mission-impossible-lima-invalide                             CR-MissionImpossibleLimaInvalide,
        cr-mission-impossible-zone-hors-fuseau                          CR-MissionImpossibleZoneHorsFuseau,
        cr-rapport-de-force-defavorable                                 CR-RapportDeForceDefavorable,
        cr-terrain-difficile                                            CR-TerrainDifficile,
        cr-plus-de-carburant                                            CR-PlusDeCarburant,
        cr-dispositif-disperse                                          CR-DispositifDisperse,
        cr-debut-neutralisation                                         CR-DebutNeutralisation,
        cr-fin-neutralisation                                           CR-FinNeutralisation,      
        cr-debut-silence-radio                                          CR-DebutSilenceRadio,
        cr-fin-silence-radio                                            CR-FinSilenceRadio,
        cr-debut-silence-radar                                          CR-DebutSilenceRadar,
        cr-fin-silence-radar                                            CR-FinSilenceRadar,
        cr-tir-restreint                                                CR-TirRestreint,
        cr-tir-interdit                                                 CR-TirInterdit,
        cr-tir-libre                                                    CR-TirLibre,
        cr-unite-detectee                                               CR-UniteDetectee,
        cr-unite-amie-reconnue                                          CR-UniteAmieReconnue,
        cr-unite-ennemie-reconnue                                       CR-UniteEnnemieReconnue,
        cr-unite-neutre-reconnue                                        CR-UniteNeutreReconnue,
        cr-unite-amie-identifiee                                        CR-UniteAmieIdentifiee,
        cr-unite-ennemie-identifiee                                     CR-UniteEnnemieIdentifiee,
        cr-unite-neutre-identifiee                                      CR-UniteNeutreIdentifiee,        
        cr-objet-detecte                                                CR-ObjetDetecte,
        
        -- adaptation
        cr-trace                                                        CR-Trace,
        cr-trace-id                                                     CR-TraceID,
       
        -- Reaction Populations
        cr-emploi-force-interdit                                        CR-EmploiForceInterdit,                 
        cr-maintien-a-distance-par-moyens-non-letaux                    CR-MaintienADistanceParMoyensNonLetaux ,       
        cr-dispersion-par-moyens-de-defense-actifs                      CR-DispersionParMoyensDeDefenseActifs,
        cr-armes-letales-autorisees                                     CR-ArmesLetalesAutorisees,          
        cr-population-detectee                                          CR-PopulationDetectee,
        cr-prise-a-partie-par-population                                CR-PriseAPartieParPopulation,
        cr-riposte-contre-population                                    CR-RiposteContrePopulation,
        cr-population-dangereuse-a-proximite                            CR-PopulationDangereuseAProximite,
        cr-esquive-face-a-population                                    CR-EsquiveFaceAPopulation,
        cr-decrochage-face-a-population                                 CR-DecrochageFaceAPopulation,
        cr-mise-en-place-controle-de-foule                              CR-MiseEnPlaceControleDeFoule,
        cr-mise-en-place-filtrage                                       CR-MiseEnPlaceFiltrage,
        cr-animation-barrage                                            CR-AnimationBarrage,
        cr-animation-canalisation                                       CR-AnimationCanalisation,
        cr-collecte-renseignements-sur-populations                      CR-CollecteRenseignementsSurPopulations,
        cr-population-reconnue                                          CR-PopulationReconnue,
        cr-situation-difficilement-tenable-face-a-population            CR-SituationDifficilementTenableFaceAPopulation,
        cr-utilisation-armes-non-letales-face-a-population              CR-UtilisationArmesNonLetalesFaceAPopulation,
        cr-utilisation-moyens-defense-actifs-face-a-population          CR-UtilisationMoyensDefenseActifsFaceAPopulation,
        cr-utilisation-armements-face-a-population                      CR-UtilisationArmementsFaceAPopulation,
        cr-debut-intervention-face-a-population                         CR-DebutInterventionFaceAPopulation,
        cr-population-victime-affrontements                             CR-PopulationVictimeAffrontements,
        
        -- Populations provisions
        cr-attitude-population                                          CR-AttitudePopulation,
        cr-aggravation-attitude                                         CR-AggravationAttitude,
        cr-affrontement-avec-forces-ennemies                            CR-AffrontementAvecForcesEnnemies,
        cr-population-temporairement-controlee                          CR-PopulationTemporairementControlee,
        cr-population-temporairement-repoussee                          CR-PopulationTemporairementRepoussee,
        cr-reprise-des-affrontements                                    CR-RepriseDesAffrontements,
        cr-agression-de-population                                      CR-AgressionDePopulation,
        cr-agression-par-population                                     CR-AgressionParPopulation,
        cr-riposte-contre-agression-par-population                      CR-RiposteContreAgressionParPopulation,
        cr-attaque-installation                                         CR-AttaqueInstallation,
        cr-en-stationnement                                             CR-EnStationnement,
        cr-bloquee                                                      CR-Bloquee,
        cr-filtree                                                      CR-Filtree,
        cr-attentat-terroriste-dans-population                          CR-AttentatTerroristeDansPopulation,
        cr-population-victime-explosion-mines                           CR-PopulationVictimeExplosionMines,

        -- Menaces Asymetriques
        cr-execution-attentat                                           CR-ExecutionAttentat

    }
}

END -- ScipioCR
