--
-- file name : ScipioAutomateMission.asn
--
-- Messages des différentes missions automate logistique
--

ScipioAutomateMission_LOG DEFINITIONS AUTOMATIC TAGS ::= BEGIN

IMPORTS ListAgent, Agent, Direction, OID, CoordUTM, Point, ListPoint, EnumUnitIdentificationLevel, Segment, GDH, Localisation FROM ScipioBase;

Mission-Automate-LOG-SeDeployer ::= SEQUENCE
{
    position-deploiement Point OPTIONAL
}

Mission-Automate-LOG-AppuyerMouvement ::= SEQUENCE
{
    unites-a-appuyer ListAgent
}

Mission-Automate-LOG-ReconnaitreItineraire ::= SEQUENCE
{
    itineraire-log Itineraire
}

Mission-Automate-LOG-Surveiller ::= SEQUENCE
{
    zone Polygon
}

Mission-Automate-LOG-AppuyerMouvementDansZone ::= SEQUENCE
{
    zone Polygon
}

Mission-Automate-LOG-MettreEnOeuvreZoneStationnement ::= SEQUENCE
{
    zone Polygon
}

Mission-Automate-LOG-AppuyerFranchissementDansZone ::= SEQUENCE
{
    zone Polygon
}

Mission-Automate-LOG-BloquerZone ::= SEQUENCE
{
    zone Polygon
}

Mission-Automate-LOG-ReconnaitreZoneContaminee ::= SEQUENCE
{
    zone Polygon
}

Mission-Automate-LOG-ReconnaitreZoneDeDeploiement ::= SEQUENCE
{
    zone Polygon
}

Mission-Automate-LOG-ArmerPIAs ::= SEQUENCE
{
    -- LIA obligatoire    
}

END -- ScipioAutomateMission_LOG
