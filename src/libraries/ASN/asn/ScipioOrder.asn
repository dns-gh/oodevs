--
-- file name : ScipioOrder.asn
--
-- Fichier contenant les types et messages communs à tous les types d'ordres
--

ScipioOrder DEFINITIONS AUTOMATIC TAGS ::= BEGIN

IMPORTS OID, Point, CoordUTM, GDH FROM ScipioBase
IMPORTS LimasOrder FROM ScipioLimaLimite;

EnumOrderErrorCode ::= ENUMERATED
{
    no-error                                (0),
    error-invalid-unit                      (1),
    error-invalid-limit                     (2),
    error-invalid-lima                      (3),
    error-invalid-mission                   (4),
    error-invalid-mission-parameters        (5),
    error-unit-cannot-receive-order         (6),
    error-invalid-order-conduite            (7),
    error-invalid-order-mission             (8),
    error-invalid-order-initial             (9),
    error-invalid-order-conduite-parameters (10),
    error-unit-surrendered                  (11),
    error-invalid-lima-function             (12)
}

EnumOrderState ::= ENUMERATED
{
    started   (0),
    cancelled (1),
    stopped   (2)
}

OrderContext ::= SEQUENCE
{
    limite-gauche           Line OPTIONAL,
    limite-droite           Line OPTIONAL,   
    limas                   LimasOrder,
    direction-dangereuse    Direction
}


-- TEST MISSIONS GENERIQUES

MissionParameter ::= SEQUENCE
{
    null-value BOOLEAN DEFAULT FALSE,
    value      CHOICE
    {
        Agent,
        ListAgent,
        Automate,
        ListAutomate,
        BOOLEAN,
        Direction,
        KnowledgeAgent,
        ListKnowledgeAgent,
        KnowledgeObject,
        ListKnowledgeObject,
        KnowledgePopulation
    }
}

MissionParameters ::= SEQUENCE OF MissionParameter



END -- ScipioOrder
