--
-- file name : ScipioPionMissionAlat.asn
--
-- Messages des différentes missions automate Alat
--

ScipioPionMission_ALAT DEFINITIONS AUTOMATIC TAGS ::= BEGIN

Enum_ALAT_PorteeAction ::= ENUMERATED
{
    courte-portee   (0),
    moyenne-portee  (1),
    longue-portee   (2),
    sans-munitions  (3)
}

Enum_ALAT_AmbianceMission ::= ENUMERATED
{
    aa         (0),        
    as         (1),
    polyvalent (2)
} 

Mission-Pion-ALAT-ReconnaitreDansLaProfondeur ::= SEQUENCE
{
    point-regroupement              Point,
    plots-ravitaillement            ListKnowledgeObject,
    point-dislocation               Point,
    zone                            Localisation
}

Mission-Pion-ALAT-ReconnaitreContourEnnemi ::= SEQUENCE
{
    point-regroupement              Point,
    plots-ravitaillement            ListKnowledgeObject
}

Mission-Pion-ALAT-DetruireNeutraliserDansZone ::= SEQUENCE
{
    zone                            Polygon,
    point-dislocation               Point,
    cibles-prioritaires             NatureAtlas,                                
    point-regroupement              Point,
    plots-ravitaillement            ListKnowledgeObject,
    neutraliser                     BOOLEAN
}

Mission-Pion-ALAT-DetruireAeromobile ::= SEQUENCE
{
    unite-a-detruire                ListKnowledgeAgent,
    point-regroupement              Point,
    plots-ravitaillement            ListKnowledgeObject
}

Mission-Pion-ALAT-Freiner ::= SEQUENCE
{
    cibles-prioritaires             NatureAtlas,
    point-regroupement              Point,
    plots-ravitaillement            ListKnowledgeObject
}

Mission-Pion-ALAT-Attaquer ::= SEQUENCE
{
    cibles-prioritaires             NatureAtlas,
    point-regroupement              Point,
    plots-ravitaillement            ListKnowledgeObject
}

Mission-Pion-ALAT-Jalonner ::= SEQUENCE
{
    point-regroupement              Point,
    cibles-prioritaires             NatureAtlas,
    plots-ravitaillement            ListKnowledgeObject
}

Mission-Pion-ALAT-Escorter ::= SEQUENCE
{
    unites-a-escorter               ListAgent,
    point-regroupement              Point,
    cibles-prioritaires             NatureAtlas,                                
    plots-ravitaillement            ListKnowledgeObject
}

Mission-Pion-ALAT-Heliporter ::= SEQUENCE
{
    unites-a-heliporter             ListAgent,
    point-debarquement              Point,
    point-embarquement              Point,
    point-regroupement              Point,
    plots-ravitaillement            ListKnowledgeObject,
    avec-materiel                   BOOLEAN DEFAULT FALSE
}

Mission-Pion-ALAT-HeliporterHelitransporterPlotRavitaillement ::= SEQUENCE
{
    point-debarquement              Point,
    position-regroupement           Point,
    plots-ravitaillement            ListKnowledgeObject
}

Mission-Pion-ALAT-Helitransporter ::= SEQUENCE
{
    unites-a-helitransporter        ListAgent, 
    point-debarquement              Point,
    point-embarquement              Point,
    point-regroupement              Point,  
    plots-ravitaillement            ListKnowledgeObject,
    avec-materiel                   BOOLEAN DEFAULT FALSE
}

Mission-Pion-ALAT-IMEX ::= SEQUENCE
{
    unites-a-appuyer                ListAgent,
    point-regroupement              Point,
    plots-ravitaillement            ListKnowledgeObject
}

Mission-Pion-ALAT-Eclairer ::= SEQUENCE
{
    point-regroupement      Point,
    plots-ravitaillement    ListKnowledgeObject
}

Mission-Pion-ALAT-Surveiller ::= SEQUENCE
{
    zone                            Polygon,
    point-regroupement              Point,
    plots-ravitaillement            ListKnowledgeObject
}

Mission-Pion-ALAT-AppuyerDirectAuContact ::= SEQUENCE
{
    cibles-prioritaires             NatureAtlas,
    unites-a-appuyer                ListAgent,
    point-regroupement              Point,
    plots-ravitaillement            ListKnowledgeObject
}

Mission-Pion-ALAT-Couvrir ::= SEQUENCE
{
    cibles-prioritaires             NatureAtlas,
    unites-a-couvrir                ListAgent,
    point-regroupement              Point,
    plots-ravitaillement            ListKnowledgeObject
}

Mission-Pion-ALAT-AllerSeRecompleter ::= SEQUENCE
{
    plots-ravitaillement ListKnowledgeObject
}

END -- ScipioPionMission_ALAT
