--
-- file name : ScipioAutomateOrder.asn
--
-- Messages de gestion des ordres niveau automate
--

ScipioPopulationOrder DEFINITIONS AUTOMATIC TAGS ::= BEGIN

IMPORTS OID, Point, CoordUTM, GDH, Localisation FROM ScipioBase
IMPORTS Itineraire, Direction, Segment, ListAgent, ListOID FROM ScipioBase
IMPORTS EnumOrderErrorCode FROM ScipioOrder

IMPORTS Mission-Population-FaireMouvement,
        Mission-Population-Manifester,
        Mission-Population-CommettreExactions FROM ScipioPopulationMission;

Mission-Population ::= CHOICE
{
    mission-population-faire-mouvement      Mission-Population-FaireMouvement,
    mission-population-manifester           Mission-Population-Manifester,
    mission-population-commettre-exactions  Mission-Population-CommettreExactions 
}

MsgPopulationOrder ::= SEQUENCE
{
    oid-unite-executante Population,
    mission              Mission-Population
}

MsgPopulationOrderAck ::= SEQUENCE
{
    oid-unite-executante Population,
    error-code		     EnumOrderErrorCode
}

MsgPopulationOrderManagement ::= SEQUENCE
{
    oid-unite-executante    Population,
    etat                    EnumOrderState
}

END -- ScipioPopulationOrder
