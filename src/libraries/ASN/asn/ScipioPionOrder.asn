--
-- file name : ScipioPionOrder.asn
--
-- Messages de gestion des ordres niveau pion
--


ScipioPionOrder DEFINITIONS AUTOMATIC TAGS ::= BEGIN

IMPORTS ListOID, OID, Point, CoordUTM, GDH FROM ScipioBase
IMPORTS Itineraire, Point, Direction, Segment, ListAgent FROM ScipioBase
IMPORTS EnumOrderErrorCode FROM ScipioOrder

IMPORTS Mission-Pion-ALAT-ReconnaitreDansLaProfondeur,
        Mission-Pion-ALAT-ReconnaitreContourEnnemi,
        Mission-Pion-ALAT-DetruireNeutraliserDansZone,
        Mission-Pion-ALAT-DetruireAeromobile,
        Mission-Pion-ALAT-Freiner,
        Mission-Pion-ALAT-Jalonner,
        Mission-Pion-ALAT-Escorter,
        Mission-Pion-ALAT-Heliporter,
        Mission-Pion-ALAT-HeliporterHelitransporterPlotRavitaillement,
        Mission-Pion-ALAT-Helitransporter,
        Mission-Pion-ALAT-IMEX,
        Mission-Pion-ALAT-Eclairer,
        Mission-Pion-ALAT-Surveiller,
        Mission-Pion-ALAT-AppuyerDirectAuContact,
        Mission-Pion-ALAT-Couvrir,
        Mission-Pion-ALAT-Attaquer,
        Mission-Pion-ALAT-AllerSeRecompleter FROM ScipioPionMission_ALAT
        
IMPORTS Mission-Pion-ASA-DefendreSite,
        Mission-Pion-ASA-DefendreSiteAPartirPosition,
        Mission-Pion-ASA-DefendreZone,
        Mission-Pion-ASA-DefendreZoneAPartirPosition,
        Mission-Pion-ASA-Surveiller,
        Mission-Pion-ASA-DefendreUnites,
        Mission-Pion-ASA-MISTRAL-DefendreSite,
        Mission-Pion-ASA-MISTRAL-DefendreSiteAPartirPosition,
        Mission-Pion-ASA-MISTRAL-DefendreZone,
        Mission-Pion-ASA-MISTRAL-DefendreZoneAPartirPosition,
        Mission-Pion-ASA-MISTRAL-Surveiller FROM ScipioPionMission_ASA
        
IMPORTS Mission-Pion-ASS-AssurerMiseEnOeuvre,
        Mission-Pion-ASS-AssurerMiseEnOeuvreSurPosition,
        Mission-Pion-ASS-ReconnaitreZoneDeploiement,
        Mission-Pion-ASS-AcquerirLanceursEni,
        Mission-Pion-ASS-EO-AcquerirObjectifs,
        Mission-Pion-ASS-EOP-AcquerirObjectifs,
        Mission-Pion-ASS-RATAC-AcquerirObjectifs FROM ScipioPionMission_ASS
        
IMPORTS Mission-Pion-ABC-ReconnaitreAxe,
        Mission-Pion-ABC-Soutenir,
        Mission-Pion-ABC-Couvrir,
        Mission-Pion-ABC-FlancGarder,
        Mission-Pion-ABC-Reduire,
        Mission-Pion-ABC-Appuyer,
        Mission-Pion-ABC-Fixer,
        Mission-Pion-ABC-RenseignerSur,
        Mission-Pion-ABC-ControlerZone,
        Mission-Pion-ABC-Surveiller,
        Mission-Pion-ABC-Barrer ,
        Mission-Pion-ABC-Attaquer,
        Mission-Pion-ABC-ReconnaitrePoint,
        Mission-Pion-ABC-Eclairer,
        Mission-Pion-ABC-Jalonner,
        Mission-Pion-ABC-ContreAttaquer,
        Mission-Pion-ABC-SemparerZone,
        Mission-Pion-ABC-ReleverUnite,
        Mission-Pion-ABC-ArmerPIA,
        Mission-Pion-ABC-OuvrirItineraire,
        Mission-Pion-ABC-Freiner,
        Mission-Pion-ABC-EscorterUnite,
        Mission-Pion-ABC-EscorterUnites,
        Mission-Pion-ABC-RenseignerSur,
        Mission-Pion-ABC-ArmerPointDeControle, 
        Mission-Pion-ABC-OrganiserAccueilColonneRefugies,
        Mission-Pion-ABC-AppuyerSurPosition,
        Mission-Pion-ABC-RASIT-RenseignerSur  FROM ScipioPionMission_ABC
        
IMPORTS Mission-Pion-GEN-OuvrirItineraire,
        Mission-Pion-GEN-RetablirItineraire,
        Mission-Pion-GEN-ReconnaitreItineraire,
        Mission-Pion-GEN-ReconnaitreZone,
        Mission-Pion-GEN-ReconnaitreSiteFranchissement,
        Mission-Pion-GEN-EquiperExploiterSiteFranchissement,
        Mission-Pion-GEN-ExecuterVariantement,
        Mission-Pion-GEN-DegagerObstacles,
        Mission-Pion-GEN-ContournerObstacles,
        Mission-Pion-GEN-DepolluerZone,
        Mission-Pion-GEN-Renforcer,
        Mission-Pion-GEN-RealiserTravauxProtection,
        Mission-Pion-GEN-RealiserTravauxContreMobilite,
        Mission-Pion-GEN-RealiserTravauxAppuiDeploiement,
        Mission-Pion-GEN-RealiserCamps,
        Mission-Pion-GEN-ReprendreTravaux,
        Mission-Pion-GEN-AmeliorerMobilite,
        Mission-Pion-GEN-ActiverObstacle  FROM ScipioPionMission_GEN
        
IMPORTS Mission-Pion-INF-ReconnaitreAxe,
        Mission-Pion-INF-Couvrir,
        Mission-Pion-INF-Reduire,
        Mission-Pion-INF-Appuyer,
        Mission-Pion-INF-Fixer,
        Mission-Pion-INF-ControlerSecteur,
        Mission-Pion-INF-SurveillerSecteur,
        Mission-Pion-INF-Barrer,
        Mission-Pion-INF-ReconnaitrePoint,
        Mission-Pion-INF-Eclairer,
        Mission-Pion-INF-Interdire,
        Mission-Pion-INF-Semparer,
        Mission-Pion-INF-PrendrePreciserContact,
        Mission-Pion-INF-Defendre,
        Mission-Pion-INF-DetruireEmbuscade,
        Mission-Pion-INF-ContreAttaquer,
        Mission-Pion-INF-Freiner,
        Mission-Pion-INF-FlancGarder,
        Mission-Pion-INF-OrganiserUnCheckPoint,
        Mission-Pion-INF-Harceler,
        Mission-Pion-INF-DetruireParCoupDeMain,
        Mission-Pion-INF-EscorterUnite,
        Mission-Pion-INF-EscorterUnites,
        Mission-Pion-INF-RenseignerSur,
        Mission-Pion-INF-Soutenir,
        Mission-Pion-INF-Securiser,
        Mission-Pion-INF-Recueillir,
        Mission-Pion-INF-RepondreAAggression, 
        Mission-Pion-INF-AppuyerSurPosition FROM ScipioPionMission_INF
        
IMPORTS Mission-Pion-LOG-SeDeployer,
        Mission-Pion-LOG-Renforcer,
        Mission-Pion-LOG-PreparerBascule,
        Mission-Pion-LOG-DecontaminerBlesses,
        Mission-Pion-LOG-TrierEtTraiterBlesses,
        Mission-Pion-LOG-TrierBlesses,
        Mission-Pion-LOG-TraiterBlesses,        
        Mission-Pion-LOG-PrendreEnCompteReactionsMentales,
        Mission-Pion-LOG-Convoyer,
        Mission-Pion-LOG-Reparer,
        Mission-Pion-LOG-AppuyerMouvement,
        Mission-Pion-LOG-ReconnaitreItineraire,
        Mission-Pion-LOG-ReconnaitreZoneContaminee,
        Mission-Pion-LOG-AppuyerMouvementDansZone,
        Mission-Pion-LOG-MettreEnOeuvreZoneStationnement,
        Mission-Pion-LOG-AppuyerFranchissementSurUnPoint,
        Mission-Pion-LOG-BloquerZone,
        Mission-Pion-LOG-ReconnaitreZoneDeDeploiement,
        Mission-Pion-LOG-ArmerPIA,
        Mission-Pion-LOG-Surveiller FROM ScipioPionMission_LOG
        
IMPORTS Mission-Pion-Test-MoveTo,
        Mission-Pion-Test-CreateObject,
        Mission-Pion-Test-DestroyObject,
        Mission-Pion-Test-CreateBypass,
        Mission-Pion-Test-Fire,
        Mission-Pion-Test-ChangePosture,
        Mission-Pion-Test-PathFind,
        Mission-Pion-Test-FindPosition,
        Mission-Pion-Test-Reinforce,
        Mission-Pion-Test-Heliporter,
        Mission-Pion-PlastronEnnemi,
        Mission-Pion-FaireMouvement,
        Mission-Pion-Suivre,
        Mission-Pion-Transporter,
        Mission-Pion-SeFaireDecontaminer,
        Mission-Pion-Franchir,
        Mission-Pion-Decrocher,
        Mission-Pion-Stationner,
        Mission-Pion-SeFaireTransporter,
        Mission-Pion-InterdireFranchissementPopulations,
        Mission-Pion-FiltrerPopulations,
        Mission-Pion-RenseignerSurPopulations,
        Mission-Pion-CanaliserPopulations,
        Mission-Pion-ControlerPopulationsDansZones,
        Mission-Pion-SecuriserZoneContrePopulations,
        Mission-Pion-Generique,
        Mission-Pion-MILICE-Provoquer,
        Mission-Pion-MILICE-PrendreEtTenir,
        Mission-Pion-MILICE-DetruireEmbuscade,
        Mission-Pion-JOINT-AIR-EffectuerRaid,
        Mission-Pion-ASY-SInfiltrer,
        Mission-Pion-ASY-CommettreAttentatContrePopulation,
        Mission-Pion-ASY-CommettreAttentatContreInstallation,
        Mission-Pion-ASY-CommettreAttentatContreForcesArmees,
        Mission-Pion-ASY-CommettreExactionsSurPopulationDansZone,
        Mission-Pion-ASY-Renseigner FROM ScipioPionMission_Misc
        
IMPORTS Mission-Pion-NBC-AnimerUnPlotDeDecontamination,
        Mission-Pion-NBC-ReconnaitreItineraire,
        Mission-Pion-NBC-ReconnaitreZone,
        Mission-Pion-NBC-DecontaminerZone,
        Mission-Pion-NBC-ReconnaitreUnSiteROTA FROM ScipioPionMission_NBC
        
IMPORTS Mission-Pion-RENS-ROHUM-RenseignerSur,
        Mission-Pion-RENS-ROHUM-SExfiltrer,
        Mission-Pion-RENS-ROHUM-OrienterGuider,        
        Mission-Pion-RENS-ROIM-MettreEnOeuvre,
        Mission-Pion-RENS-ROIM-SDTI-RenseignerSur,
        Mission-Pion-RENS-ROIM-CL289-RenseignerSur,
        Mission-Pion-RENS-ROEM-Appuyer,        
        Mission-Pion-RENS-ROEM-RenseignerSur,
        Mission-Pion-RENS-ROEM-MettreEnOeuvre,
        Mission-Pion-RENS-RADINT-RenseignerSur,
        Mission-Pion-RENS-RADINT-MettreEnOeuvre FROM ScipioPionMission_RENS
        
IMPORTS Mission-Pion-TRANS-EtablirGererLiaison FROM ScipioPionMission_TRANS;       


Mission-Pion ::= CHOICE
{
    mission-pion-alat-aller-se-recompleter                              Mission-Pion-ALAT-AllerSeRecompleter,
    mission-pion-alat-reconnaitre-dans-la-profondeur                    Mission-Pion-ALAT-ReconnaitreDansLaProfondeur,
    mission-pion-alat-reconnaitre-contour-ennemi                        Mission-Pion-ALAT-ReconnaitreContourEnnemi,
    mission-pion-alat-detruire-neutraliser-dans-zone                    Mission-Pion-ALAT-DetruireNeutraliserDansZone,
    mission-pion-alat-detruire-aeromobile                               Mission-Pion-ALAT-DetruireAeromobile,
    mission-pion-alat-freiner                                           Mission-Pion-ALAT-Freiner,
    mission-pion-alat-jalonner                                          Mission-Pion-ALAT-Jalonner,
    mission-pion-alat-escorter                                          Mission-Pion-ALAT-Escorter,
    mission-pion-alat-heliporter                                        Mission-Pion-ALAT-Heliporter,
    mission-pion-alat-heliporter-helitransporter-plot-ravitaillement    Mission-Pion-ALAT-HeliporterHelitransporterPlotRavitaillement,
    mission-pion-alat-helitransporter                                   Mission-Pion-ALAT-Helitransporter,
    mission-pion-alat-imex                                              Mission-Pion-ALAT-IMEX,
    mission-pion-alat-eclairer                                          Mission-Pion-ALAT-Eclairer,
    mission-pion-alat-surveiller                                        Mission-Pion-ALAT-Surveiller,
    mission-pion-alat-appuyer-direct-au-contact                         Mission-Pion-ALAT-AppuyerDirectAuContact,
    mission-pion-alat-couvrir                                           Mission-Pion-ALAT-Couvrir,        
    mission-pion-alat-attaquer                                          Mission-Pion-ALAT-Attaquer,        
    mission-pion-asa-defendre-site                                      Mission-Pion-ASA-DefendreSite,
    mission-pion-asa-defendre-site-a-partir-position                    Mission-Pion-ASA-DefendreSiteAPartirPosition,
    mission-pion-asa-defendre-zone                                      Mission-Pion-ASA-DefendreZone,
    mission-pion-asa-defendre-zone-a-partir-position                    Mission-Pion-ASA-DefendreZoneAPartirPosition,
    mission-pion-asa-surveiller                                         Mission-Pion-ASA-Surveiller,
    mission-pion-asa-defendre-unites                                    Mission-Pion-ASA-DefendreUnites,        
    mission-pion-asa-mistral-defendre-site                              Mission-Pion-ASA-MISTRAL-DefendreSite,
    mission-pion-asa-mistral-defendre-site-a-partir-position            Mission-Pion-ASA-MISTRAL-DefendreSiteAPartirPosition,
    mission-pion-asa-mistral-defendre-zone                              Mission-Pion-ASA-MISTRAL-DefendreZone,
    mission-pion-asa-mistral-defendre-zone-a-partir-position            Mission-Pion-ASA-MISTRAL-DefendreZoneAPartirPosition,
    mission-pion-asa-mistral-surveiller                                 Mission-Pion-ASA-MISTRAL-Surveiller,
    mission-pion-ass-assurer-mise-en-oeuvre                             Mission-Pion-ASS-AssurerMiseEnOeuvre,
    mission-pion-ass-assurer-mise-en-oeuvre-sur-position                Mission-Pion-ASS-AssurerMiseEnOeuvreSurPosition,
    mission-pion-ass-reconnaitre-zone-deploiement                       Mission-Pion-ASS-ReconnaitreZoneDeploiement,
    mission-pion-ass-acquerir-lanceurs-eni                              Mission-Pion-ASS-AcquerirLanceursEni,
    mission-pion-ass-eo-acquerir-objectifs                              Mission-Pion-ASS-EO-AcquerirObjectifs,
    mission-pion-ass-eop-acquerir-objectifs                             Mission-Pion-ASS-EOP-AcquerirObjectifs,
    mission-pion-ass-ratac-acquerir-objectifs                           Mission-Pion-ASS-RATAC-AcquerirObjectifs,
    mission-pion-abc-reconnaitre-axe                                    Mission-Pion-ABC-ReconnaitreAxe,
    mission-pion-abc-soutenir                                           Mission-Pion-ABC-Soutenir,
    mission-pion-abc-couvrir                                            Mission-Pion-ABC-Couvrir,
    mission-pion-abc-flanc-garder                                       Mission-Pion-ABC-FlancGarder,
    mission-pion-abc-reduire                                            Mission-Pion-ABC-Reduire,
    mission-pion-abc-appuyer                                            Mission-Pion-ABC-Appuyer,
    mission-pion-abc-fixer                                              Mission-Pion-ABC-Fixer,
    mission-pion-abc-renseigner-sur                                     Mission-Pion-ABC-RenseignerSur,
    mission-pion-abc-controler-zone                                     Mission-Pion-ABC-ControlerZone,
    mission-pion-abc-surveiller                                         Mission-Pion-ABC-Surveiller,
    mission-pion-abc-barrer                                             Mission-Pion-ABC-Barrer,
    mission-pion-abc-attaquer                                           Mission-Pion-ABC-Attaquer,
    mission-pion-abc-reconnaitre-point                                  Mission-Pion-ABC-ReconnaitrePoint,
    mission-pion-abc-eclairer                                           Mission-Pion-ABC-Eclairer,
    mission-pion-abc-jalonner                                           Mission-Pion-ABC-Jalonner,
    mission-pion-abc-contre-attaquer                                    Mission-Pion-ABC-ContreAttaquer,
    mission-pion-abc-semparer-zone                                      Mission-Pion-ABC-SemparerZone,
    mission-pion-abc-relever-unite                                      Mission-Pion-ABC-ReleverUnite,
    mission-pion-abc-armer-pia                                          Mission-Pion-ABC-ArmerPIA,
    mission-pion-abc-ouvrir-itineraire                                  Mission-Pion-ABC-OuvrirItineraire,
    mission-pion-abc-freiner                                            Mission-Pion-ABC-Freiner,
    mission-pion-abc-escorter-unite                                     Mission-Pion-ABC-EscorterUnite,
    mission-pion-abc-escorter-unites                                    Mission-Pion-ABC-EscorterUnites, 
    mission-pion-abc-armer-point-de-controle                            Mission-Pion-ABC-ArmerPointDeControle, 
    mission-pion-abc-organiser-accueil-colonne-refugies                 Mission-Pion-ABC-OrganiserAccueilColonneRefugies,
    mission-pion-abc-appuyer-sur-position                               Mission-Pion-ABC-AppuyerSurPosition,    
    mission-pion-abc-rasit-renseigner-sur                               Mission-Pion-ABC-RASIT-RenseignerSur,
    mission-pion-gen-ouvrir-itineraire                                  Mission-Pion-GEN-OuvrirItineraire, 
    mission-pion-gen-retablir-itineraire                                Mission-Pion-GEN-RetablirItineraire, 
    mission-pion-gen-reconnaitre-itineraire                             Mission-Pion-GEN-ReconnaitreItineraire, 
    mission-pion-gen-reconnaitre-zone                                   Mission-Pion-GEN-ReconnaitreZone, 
    mission-pion-gen-reconnaitre-site-franchissement                    Mission-Pion-GEN-ReconnaitreSiteFranchissement,
    mission-pion-gen-equiper-exploiter-site-franchissement              Mission-Pion-GEN-EquiperExploiterSiteFranchissement,
    mission-pion-gen-executer-variantement                              Mission-Pion-GEN-ExecuterVariantement,
    mission-pion-gen-degager-obstacles                                  Mission-Pion-GEN-DegagerObstacles,
    mission-pion-gen-contourner-obstacles                               Mission-Pion-GEN-ContournerObstacles,
    mission-pion-gen-depolluer-zone                                     Mission-Pion-GEN-DepolluerZone,
    mission-pion-gen-renforcer                                          Mission-Pion-GEN-Renforcer,
    mission-pion-gen-realiser-travaux-protection                        Mission-Pion-GEN-RealiserTravauxProtection,
    mission-pion-gen-realiser-travaux-contre-mobilite                   Mission-Pion-GEN-RealiserTravauxContreMobilite,
    mission-pion-gen-realiser-travaux-appui-deploiement                 Mission-Pion-GEN-RealiserTravauxAppuiDeploiement,
    mission-pion-gen-realiser-camps                                     Mission-Pion-GEN-RealiserCamps,
    mission-pion-gen-reprendre-travaux                                  Mission-Pion-GEN-ReprendreTravaux,
    mission-pion-gen-ameliorer-mobilite                                 Mission-Pion-GEN-AmeliorerMobilite, 
    mission-pion-gen-activer-obstacle                                   Mission-Pion-GEN-ActiverObstacle,    
    mission-pion-inf-reconnaitre-axe                                    Mission-Pion-INF-ReconnaitreAxe,
    mission-pion-inf-couvrir                                            Mission-Pion-INF-Couvrir,
    mission-pion-inf-reduire                                            Mission-Pion-INF-Reduire,
    mission-pion-inf-appuyer                                            Mission-Pion-INF-Appuyer,
    mission-pion-inf-fixer                                              Mission-Pion-INF-Fixer,
    mission-pion-inf-controler-secteur                                  Mission-Pion-INF-ControlerSecteur,
    mission-pion-inf-surveiller-secteur                                 Mission-Pion-INF-SurveillerSecteur,
    mission-pion-inf-barrer                                             Mission-Pion-INF-Barrer,
    mission-pion-inf-reconnaitre-point                                  Mission-Pion-INF-ReconnaitrePoint,
    mission-pion-inf-eclairer                                           Mission-Pion-INF-Eclairer,
    mission-pion-inf-interdire                                          Mission-Pion-INF-Interdire,
    mission-pion-inf-semparer                                           Mission-Pion-INF-Semparer,
    mission-pion-inf-prendre-preciser-contact                           Mission-Pion-INF-PrendrePreciserContact,
    mission-pion-inf-defendre                                           Mission-Pion-INF-Defendre,
    mission-pion-inf-detruire-embuscade                                 Mission-Pion-INF-DetruireEmbuscade,
    mission-pion-inf-contre-attaquer                                    Mission-Pion-INF-ContreAttaquer,
    mission-pion-inf-freiner                                            Mission-Pion-INF-Freiner,
    mission-pion-inf-flanc-garder                                       Mission-Pion-INF-FlancGarder,
    mission-pion-inf-organiser-un-check-point                           Mission-Pion-INF-OrganiserUnCheckPoint,
    mission-pion-inf-harceler                                           Mission-Pion-INF-Harceler,
    mission-pion-inf-detruire-par-coup-de-main                          Mission-Pion-INF-DetruireParCoupDeMain,
    mission-pion-inf-escorter-unite                                     Mission-Pion-INF-EscorterUnite,
    mission-pion-inf-escorter-unites                                    Mission-Pion-INF-EscorterUnites, 
    mission-pion-inf-renseigner-sur                                     Mission-Pion-INF-RenseignerSur,
    mission-pion-inf-soutenir                                           Mission-Pion-INF-Soutenir,
    mission-pion-inf-securiser                                          Mission-Pion-INF-Securiser,
    mission-pion-inf-recueillir                                         Mission-Pion-INF-Recueillir,    
    mission-pion-inf-repondre-a-aggression                              Mission-Pion-INF-RepondreAAggression,    
    mission-pion-inf-appuyer-sur-position                               Mission-Pion-INF-AppuyerSurPosition,
    mission-pion-log-se-deployer                                        Mission-Pion-LOG-SeDeployer,    
    mission-pion-log-renforcer                                          Mission-Pion-LOG-Renforcer,
    mission-pion-log-preparer-bascule                                   Mission-Pion-LOG-PreparerBascule,    
    mission-pion-log-decontaminer-blesses                               Mission-Pion-LOG-DecontaminerBlesses,
    mission-pion-log-trier-et-traiter-blesses                           Mission-Pion-LOG-TrierEtTraiterBlesses,
    mission-pion-log-trier-blesses                                      Mission-Pion-LOG-TrierBlesses,
    mission-pion-log-traiter-blesses                                    Mission-Pion-LOG-TraiterBlesses,
    mission-pion-log-prendre-en-compte-reactions-mentales               Mission-Pion-LOG-PrendreEnCompteReactionsMentales,
    mission-pion-log-convoyer                                           Mission-Pion-LOG-Convoyer,    
    mission-pion-log-reparer                                            Mission-Pion-LOG-Reparer,           
    mission-pion-log-appuyer-mouvement                                  Mission-Pion-LOG-AppuyerMouvement,
    mission-pion-log-reconnaitre-itineraire                             Mission-Pion-LOG-ReconnaitreItineraire,
    mission-pion-log-reconnaitre-zone-contaminee                        Mission-Pion-LOG-ReconnaitreZoneContaminee,
    mission-pion-log-appuyer-mouvement-dans-zone                        Mission-Pion-LOG-AppuyerMouvementDansZone,
    mission-pion-log-mettre-en-oeuvre-zone-stationnement                Mission-Pion-LOG-MettreEnOeuvreZoneStationnement,
    mission-pion-log-appuyer-franchissement-sur-un-point                Mission-Pion-LOG-AppuyerFranchissementSurUnPoint,
    mission-pion-log-bloquer-zone                                       Mission-Pion-LOG-BloquerZone,
    mission-pion-log-reconnaitre-zone-de-deploiement                    Mission-Pion-LOG-ReconnaitreZoneDeDeploiement,
    mission-pion-log-armer-pia                                          Mission-Pion-LOG-ArmerPIA,        
    mission-pion-log-surveiller                                         Mission-Pion-LOG-Surveiller,        
    mission-pion-test-heliporter                                        Mission-Pion-Test-Heliporter,
    mission-pion-test-move-to                                           Mission-Pion-Test-MoveTo,
    mission-pion-test-create-object                                     Mission-Pion-Test-CreateObject,
    mission-pion-test-destroy-object                                    Mission-Pion-Test-DestroyObject,
    mission-pion-test-create-bypass                                     Mission-Pion-Test-CreateBypass,
    mission-pion-test-fire                                              Mission-Pion-Test-Fire,
    mission-pion-test-change-posture                                    Mission-Pion-Test-ChangePosture,
    mission-pion-test-path-find                                         Mission-Pion-Test-PathFind,
    mission-pion-test-find-position                                     Mission-Pion-Test-FindPosition,
    mission-pion-test-reinforce                                         Mission-Pion-Test-Reinforce,
    mission-pion-plastron-ennemi                                        Mission-Pion-PlastronEnnemi,
    mission-pion-faire-mouvement                                        Mission-Pion-FaireMouvement,
    mission-pion-suivre                                                 Mission-Pion-Suivre,
    mission-pion-transporter                                            Mission-Pion-Transporter,
    mission-pion-se-faire-decontaminer                                  Mission-Pion-SeFaireDecontaminer,
    mission-pion-franchir                                               Mission-Pion-Franchir,
    mission-pion-decrocher                                              Mission-Pion-Decrocher,
    mission-pion-stationner                                             Mission-Pion-Stationner,
    mission-pion-se-faire-transporter                                   Mission-Pion-SeFaireTransporter, 
    mission-pion-interdire-franchissement-populations                   Mission-Pion-InterdireFranchissementPopulations,
    mission-pion-filtrer-populations                                    Mission-Pion-FiltrerPopulations,
    mission-pion-renseigner-sur-populations                             Mission-Pion-RenseignerSurPopulations,
    mission-pion-canaliser-populations                                  Mission-Pion-CanaliserPopulations,
    mission-pion-controler-populations-dans-zone                        Mission-Pion-ControlerPopulationsDansZone,       
    mission-pion-securiser-zone-contre_populations                      Mission-Pion-SecuriserZoneContrePopulations,
    mission-pion-generique                                              Mission-Pion-Generique,       
    mission-pion-milice-provoquer                                       Mission-Pion-MILICE-Provoquer,
    mission-pion-milice-prendre-et-tenir                                Mission-Pion-MILICE-PrendreEtTenir,
    mission-pion-milice-detruire-embuscade                              Mission-Pion-MILICE-DetruireEmbuscade,
    mission-pion-joint-air-effectuer-raid                               Mission-Pion-JOINT-AIR-EffectuerRaid,
    mission-pion-nbc-animer-un-plot-de-decontamination                  Mission-Pion-NBC-AnimerUnPlotDeDecontamination,
    mission-pion-nbc-reconnaitre-itineraire                             Mission-Pion-NBC-ReconnaitreItineraire,
    mission-pion-nbc-reconnaitre-zone                                   Mission-Pion-NBC-ReconnaitreZone,
    mission-pion-nbc-decontaminer-zone                                  Mission-Pion-NBC-DecontaminerZone,
    mission-pion-nbc-reconnaitre-un-site-rota                           Mission-Pion-NBC-ReconnaitreUnSiteROTA,   
    mission-pion-rens-rohum-renseigner-sur                              Mission-Pion-RENS-ROHUM-RenseignerSur,
    mission-pion-rens-rohum-sexfiltrer                                  Mission-Pion-RENS-ROHUM-SExfiltrer,
    mission-pion-rens-rohum-orienter-guider                             Mission-Pion-RENS-ROHUM-OrienterGuider,
    mission-pion-rens-roem-appuyer                                      Mission-Pion-RENS-ROEM-Appuyer,
    mission-pion-rens-roem-renseigner-sur                               Mission-Pion-RENS-ROEM-RenseignerSur,
    mission-pion-rens-roem-mettre-en-oeuvre                             Mission-Pion-RENS-ROEM-MettreEnOeuvre,
    mission-pion-rens-radint-renseigner-sur                             Mission-Pion-RENS-RADINT-RenseignerSur,
    mission-pion-rens-radint-mettre-en-oeuvre                           Mission-Pion-RENS-RADINT-MettreEnOeuvre,
    mission-pion-rens-roim-mettre-en-oeuvre                             Mission-Pion-RENS-ROIM-MettreEnOeuvre,     
    mission-pion-rens-roim-sdti-renseigner-sur                          Mission-Pion-RENS-ROIM-SDTI-RenseignerSur,
    mission-pion-rens-roim-cl289-renseigner-sur                         Mission-Pion-RENS-ROIM-CL289-RenseignerSur,
    mission-pion-trans-etablir-gerer-liaison                            Mission-Pion-TRANS-EtablirGererLiaison,
    mission-pion-asy-sinfiltrer                                         Mission-Pion-ASY-SInfiltrer,
    mission-pion-asy-commettre-attentatContrePopulation                 Mission-Pion-ASY-CommettreAttentatContrePopulation,
    mission-pion-asy-commettre-attentatContreForcesArmees               Mission-Pion-ASY-CommettreAttentatContreForcesArmees,
    mission-pion-asy-commettre-attentatContreInstallation               Mission-Pion-ASY-CommettreAttentatContreInstallation,
    mission-pion-asy-commettre-exactions-sur-population-dans-zone       Mission-Pion-ASY-CommettreExactionsSurPopulationDansZone,
    mission-pion-asy-renseigner                                         Mission-Pion-ASY-Renseigner
}

MsgPionOrder ::= SEQUENCE
{
    oid-unite-executante    Agent,
    order-context           OrderContext,
    mission                 Mission-Pion
}

MsgPionOrderAck ::= SEQUENCE
{
    oid-unite-executante    Agent,
    error-code				EnumOrderErrorCode
}

MsgPionOrderManagement ::= SEQUENCE
{
    oid-unite-executante    Agent,
    etat                    EnumOrderState
}

END -- ScipioOrder
