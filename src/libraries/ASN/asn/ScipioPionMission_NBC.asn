--
-- file name : ScipioPionMission_NBC.asn
--
-- Messages des différentes missions pion NBC
--

ScipioPionMission_NBC DEFINITIONS AUTOMATIC TAGS ::= BEGIN

Mission-Pion-NBC-AnimerUnPlotDeDecontamination ::= SEQUENCE
{
    position-site-decontamination Point
}

Mission-Pion-NBC-ReconnaitreItineraire::= SEQUENCE
{
    itineraire  Itineraire
}

Mission-Pion-NBC-ReconnaitreZone ::= SEQUENCE
{
    zone   Polygon
}

Mission-Pion-NBC-DecontaminerZone ::= SEQUENCE
{
    zone   Polygon
}

Mission-Pion-NBC-ReconnaitreUnSiteROTA ::= SEQUENCE
{
    site-ROTA   KnowledgeObject
}

END -- ScipioPionMission_NBC
