--
-- file name : ScipioAutomateMissionAlat.asn
--
-- Messages des différentes missions automate Alat
--

ScipioAutomateMission_ALAT DEFINITIONS AUTOMATIC TAGS ::= BEGIN

IMPORTS ListAgent, Agent, Direction, OID, CoordUTM, NatureAtlas, ListPolygon, Point, Itineraire, EnumUnitIdentificationLevel, Segment, GDH, Localisation FROM ScipioBase
IMPORTS Enum_ALAT_PorteeAction, Enum_ALAT_AmbianceMission FROM ScipioPionMission_ALAT;
        
Mission-Automate-ALAT-Heliporter ::= SEQUENCE
{
    unites-a-heliporter             ListAgent,
    point-debarquement              Point,
    point-embarquement              Point,
    point-regroupement              Point,
    plots-ravitaillement            ListKnowledgeObject,
    avec-materiel                   BOOLEAN DEFAULT FALSE
}

Mission-Automate-ALAT-Jalonner ::= SEQUENCE
{
    cibles-prioritaires             NatureAtlas,   
    point-regroupement              Point,
    plots-ravitaillement            ListKnowledgeObject
}

Mission-Automate-ALAT-Helitransporter ::= SEQUENCE
{
    unites-a-helitransporter        ListAgent,
    point-debarquement              Point,
    point-embarquement              Point,
    point-regroupement              Point,
    plots-ravitaillement            ListKnowledgeObject,
    avec-materiel                   BOOLEAN DEFAULT FALSE
}

Mission-Automate-ALAT-Appuyer ::= SEQUENCE
{
    unites-a-appuyer                ListAgent,
    point-regroupement              Point,
    cibles-prioritaires             NatureAtlas,    
    plots-ravitaillement            ListKnowledgeObject,
    point-dislocation               Point,
    zone                            Polygon
}

Mission-Automate-ALAT-Couvrir ::= SEQUENCE
{
    unites-a-appuyer                ListAgent,
    point-regroupement              Point,
    cibles-prioritaires             NatureAtlas,    
    plots-ravitaillement            ListKnowledgeObject
}

Mission-Automate-ALAT-Surveiller ::= SEQUENCE
{
    zone                            Polygon,
    point-regroupement              Point,
    plots-ravitaillement            ListKnowledgeObject,
    point-logistique                Point
}

Mission-Automate-ALAT-Reconnaitre ::= SEQUENCE
{
    pointRegroupement               Point,
    plots-ravitaillement            ListKnowledgeObject
}

Mission-Automate-ALAT-Freiner ::= SEQUENCE
{
    cibles-prioritaires             NatureAtlas,                                
    point-regroupement              Point,  
    plots-ravitaillement            ListKnowledgeObject
}

Mission-Automate-ALAT-Escorter::= SEQUENCE
{
    unites-a-escorter               ListAgent,
    cibles-prioritaires             NatureAtlas,
    point-regroupement              Point,
    plots-ravitaillement            ListKnowledgeObject
}

Mission-Automate-ALAT-Attaquer ::= SEQUENCE
{
    cibles-prioritaires             NatureAtlas,
    point-regroupement              Point,
    plots-ravitaillement            ListKnowledgeObject
}

Mission-Automate-ALAT-RecueillirFormationAeromobile ::= SEQUENCE
{
    -- LIA obligatoire
    zone                            Polygon,
    cibles-prioritaires             NatureAtlas,
    point-regroupement              Point,
    plots-ravitaillement            ListKnowledgeObject
}

Mission-Automate-ALAT-AttaquerFormationAeromobile ::= SEQUENCE
{
    unites-a-attaquer               ListKnowledgeAgent,
    point-regroupement              Point,
    plots-ravitaillement            ListKnowledgeObject
}

Mission-Automate-ALAT-DonnerCoupArret ::= SEQUENCE
{
    zone                            Polygon,
    cibles-prioritaires             NatureAtlas,
    point-regroupement              Point,
    plots-ravitaillement            ListKnowledgeObject
}

Mission-Automate-ALAT-DetruireNeutraliserDansProfondeur ::= SEQUENCE
{
    zone                            Polygon,
    cibles-prioritaires             NatureAtlas,
    point-regroupement              Point,    
    point-dislocation               Point,    
    plots-ravitaillement            ListKnowledgeObject,
    neutraliser                     BOOLEAN
}

Mission-Automate-ALAT-DetruireNeutraliserDansZone ::= SEQUENCE
{
    zone                            Polygon,
    cibles-prioritaires             NatureAtlas,
    point-regroupement              Point,    
    point-dislocation               Point,    
    plots-ravitaillement            ListKnowledgeObject,
    neutraliser                     BOOLEAN
}

Mission-Automate-ALAT-AllerSeRecompleter ::= SEQUENCE
{
    plots-ravitaillement ListKnowledgeObject
}

END -- ScipioAutomateMission_ALAT
