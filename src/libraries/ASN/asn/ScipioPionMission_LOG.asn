--
-- file name : ScipioPionMission_Logistique.asn
--
-- Messages des différentes missions pion logistique
--

ScipioPionMission_LOG DEFINITIONS AUTOMATIC TAGS ::= BEGIN

-- COMMUNES
Mission-Pion-LOG-SeDeployer ::= SEQUENCE
{
    position-deploiement Point OPTIONAL
}

Mission-Pion-LOG-Renforcer ::= SEQUENCE
{
    lieu-renforcement   Point,
    automate            Automate
}

Mission-Pion-LOG-PreparerBascule ::= SEQUENCE
{
    automate-pour-bascule Automate,
    rester-sur-place      BOOLEAN
}

-- SANTE

Mission-Pion-LOG-DecontaminerBlesses ::= SEQUENCE
{
    position-deploiement Point OPTIONAL
}

Mission-Pion-LOG-TrierEtTraiterBlesses ::= SEQUENCE
{
    blessures-traitees   SantePriorites,
    position-deploiement Point OPTIONAL
}

Mission-Pion-LOG-TrierBlesses ::= SEQUENCE
{
    position-deploiement Point OPTIONAL
}

Mission-Pion-LOG-TraiterBlesses ::= SEQUENCE
{
    blessures-traitees   SantePriorites,
    position-deploiement Point OPTIONAL    
}

Mission-Pion-LOG-PrendreEnCompteReactionsMentales ::= SEQUENCE
{
    position-deploiement Point OPTIONAL
}

-- RAV

Mission-Pion-LOG-Convoyer ::= SEQUENCE
{
}

-- MAINTENANCE

Mission-Pion-LOG-Reparer ::= SEQUENCE
{
    position-deploiement Point OPTIONAL
}

-- CIRCULATION

Mission-Pion-LOG-AppuyerMouvement ::= SEQUENCE
{
    unite-a-appuyer Agent
}

Mission-Pion-LOG-ReconnaitreItineraire ::= SEQUENCE
{
    itineraire-log Itineraire
}

Mission-Pion-LOG-Surveiller ::= SEQUENCE
{
    zone Polygon
}

Mission-Pion-LOG-ReconnaitreZoneContaminee ::= SEQUENCE
{
    zone Polygon
}

Mission-Pion-LOG-AppuyerMouvementDansZone ::= SEQUENCE
{
    zone Polygon
}

Mission-Pion-LOG-MettreEnOeuvreZoneStationnement ::= SEQUENCE
{
    zone Polygon
}

Mission-Pion-LOG-AppuyerFranchissementSurUnPoint ::= SEQUENCE
{
    pont-flottant KnowledgeObject
}

Mission-Pion-LOG-BloquerZone ::= SEQUENCE
{
    zone Polygon
}

Mission-Pion-LOG-ReconnaitreZoneDeDeploiement ::= SEQUENCE
{
    zone Polygon
}

Mission-Pion-LOG-ArmerPIA ::= SEQUENCE
{
    point Point
}

END -- ScipioPionMission_LOG
