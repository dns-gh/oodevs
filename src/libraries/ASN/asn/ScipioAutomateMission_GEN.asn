--
-- file name : ScipioAutomateMission.asn
--
-- Messages des différentes missions automate génie
--

ScipioAutomateMission_GEN DEFINITIONS AUTOMATIC TAGS ::= BEGIN

IMPORTS ListAgent, Agent, Direction, OID, CoordUTM, Point, ListPoint, EnumUnitIdentificationLevel, Segment, GDH, Localisation FROM ScipioBase
IMPORTS EnumMissionGenSousTypeObstacle FROM ScipioObject;

MissionGenObject ::= SEQUENCE
{
    type           EnumObjectType,
    position       Localisation,
    preliminaire   EnumMissionGenSousTypeObstacle DEFAULT preliminaire,
    densite        REAL(0..5) DEFAULT 0,
    tc2            Automate   DEFAULT 0
}
ListMissionGenObject ::= SEQUENCE OF MissionGenObject;

----

Mission-Automate-GEN-SeDeployer ::= SEQUENCE
{
    zone Polygon 
}
Mission-Automate-GEN-ReconnaitreZone ::= SEQUENCE
{
    zone Polygon
}
Mission-Automate-GEN-RealiserTravaux ::= SEQUENCE
{
    travaux ListMissionGenObject
}
Mission-Automate-GEN-OuvrirItineraires ::= SEQUENCE
{
    itineraires ListItineraire
}
Mission-Automate-GEN-RetablirItineraires ::= SEQUENCE
{
    itineraires ListItineraire
}
Mission-Automate-GEN-FaireFranchir ::= SEQUENCE
{
    sites-de-franchissement ListKnowledgeObject,
    zone-regroupement       Localisation
}
Mission-Automate-GEN-FranchirDeViveForce ::= SEQUENCE
{
    obstacles ListKnowledgeObject
}
Mission-Automate-GEN-DegagerObstaclesDansZone ::= SEQUENCE
{
    obstacles ListKnowledgeObject
}

END -- ScipioAutomateMission_GEN
