Protocol DEFINITIONS AUTOMATIC TAGS ::= BEGIN

SimpleTest ::= SEQUENCE
{
    name VisibleString
}

CompositeStringTest ::= SEQUENCE
{
    test SEQUENCE OF SimpleTest
}

CompositeIntegerTest ::= SEQUENCE
{
    test SEQUENCE OF INTEGER
}

END
